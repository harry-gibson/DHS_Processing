FME workspace attach_regionnames_to_cluster_output_electric.fmw

Parameters:
- SourceDataset_CSV = \\129.67.26.176\map_data\DHS_Automation\Processing\HouseholdElectricity_201511\Out\All\ElectricityEtcByCluster_All_WithRegion.csv   # Source CSV (CommaSeparatedValue) File(s)
- DestDataset_CSV = \\129.67.26.176\map_data\DHS_Automation\Processing\HouseholdElectricity_201511\Out\All   # Destination CSV (CommaSeparatedValue) Folder

Readers:
- CSV_1: CSV from $(SourceDataset_CSV)

Writers:
- CSV_2: CSV to $(DestDataset_CSV)

Note: Followup request number 2: attach the region names as well as the IDs(!)
ElectricityEtcByCluster_All_WithRegion (reader CSV_1)
    attributes: SurveyID number(4,0), Country char(26), ISO3 char(4), Year char(8), HV001_Cluster number(8,0), HV024_SvyRegionID number(3,0), Spatial_LATNUM number(17,13), Spatial_LONGNUM number(15,11), HV206_HasElectricity._Count number(5,0), HV206_HasElectricity._Sum number(4,0), HV207_HasRadio._Count number(5,0), HV207_HasRadio._Sum number(4,0), HV208_HasTelevision._Count number(5,0), HV208_HasTelevision._Sum number(4,0), HV209_HasRefrigerator._Count number(5,0), HV209_HasRefrigerator._Sum number(4,0), HV210_HasBicycle._Count number(5,0), HV210_HasBicycle._Sum number(4,0), HV211_HasMotorbike._Count number(5,0), HV211_HasMotorbike._Sum number(4,0), HV212_HasCar._Count number(5,0), HV212_HasCar._Sum number(3,0), HV221_HasTelephone._Count number(5,0), HV221_HasTelephone._Sum number(4,0)
    -> Joiner
Joiner
    DATASET = \\129.67.26.176\map_data\DHS_Automation\SupportingInfo\DHS_Boundary_Data\full_download\sdr_subnational_boundaries_all_surveys.gdb
    FILEGDB_QUERY_FEATURE_TYPES_FOR_MERGE_FILTERS = Yes
    TABLE = dhs_subnational_boundaries_all_surveys
    FORMAT = FILEGDB
    ADDED_FIELDS = DHSREGEN REGNAME LEVELCO SVYNOTES
    MATCH_RULE_DISPLAY = Must Match Zero or One (1:0..1)
    JOIN_KEYS = SurveyID SVYID HV024_SvyRegionID REGCODE
    JOINED -> AttributeRenamer
AttributeRenamer
    ATTR_LIST = DHSREGEN,Spatial_RegionNameDHS,,REGNAME,Spatial_RegionNameOther,,LEVELCO,Spatial_RegionDescription,,SVYNOTES,Spatial_RegionationStrategy,
    -> ElectricityEtcByCluster_All_WithRegionAndName (writer CSV_2)
ElectricityEtcByCluster_All_WithRegionAndName (writer CSV_2)
    attributes: SurveyID number(4,0), Country char(26), ISO3 char(4), Year char(8), HV001_Cluster number(8,0), HV024_SvyRegionID number(3,0), Spatial_LATNUM number(17,13), Spatial_LONGNUM number(15,11), Spatial_RegionNameDHS auto, Spatial_RegionNameOther auto, Spatial_RegionDescription auto, Spatial_RegionationStrategy auto, HV206_HasElectricity._Count number(5,0), HV206_HasElectricity._Sum number(4,0), HV207_HasRadio._Count number(5,0), HV207_HasRadio._Sum number(4,0), HV208_HasTelevision._Count number(5,0), HV208_HasTelevision._Sum number(4,0), HV209_HasRefrigerator._Count number(5,0), HV209_HasRefrigerator._Sum number(4,0), HV210_HasBicycle._Count number(5,0), HV210_HasBicycle._Sum number(4,0), HV211_HasMotorbike._Count number(5,0), HV211_HasMotorbike._Sum number(4,0), HV212_HasCar._Count number(5,0), HV212_HasCar._Sum number(3,0), HV221_HasTelephone._Count number(5,0), HV221_HasTelephone._Sum number(4,0)
