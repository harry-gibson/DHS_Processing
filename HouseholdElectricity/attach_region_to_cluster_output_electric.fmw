FME workspace attach_region_to_cluster_output_electric.fmw

Parameters:
- SourceDataset_CSV_3 = \\129.67.26.176\map_data\DHS_Automation\Processing\HouseholdElectricity_201511\Out\All\ElectricityEtcByCluster_All.csv   # Source CSV (CommaSeparatedValue) File(s)
- DestDataset_CSV = \\129.67.26.176\map_data\DHS_Automation\Processing\HouseholdElectricity_201511\Out\All   # Destination CSV (CommaSeparatedValue) Folder

Readers:
- CSV_2: CSV from $(SourceDataset_CSV_3)

Writers:
- CSV_1: CSV to $(DestDataset_CSV)

ElectricityEtcByCluster_All (reader CSV_2)
    attributes: SurveyID number(4,0), Country char(26), ISO3 char(4), Year char(8), HV001_Cluster number(8,0), Spatial_LATNUM number(17,13), Spatial_LONGNUM number(15,11), HV206_HasElectricity._Count number(5,0), HV206_HasElectricity._Sum number(4,0), HV207_HasRadio._Count number(5,0), HV207_HasRadio._Sum number(4,0), HV208_HasTelevision._Count number(5,0), HV208_HasTelevision._Sum number(4,0), HV209_HasRefrigerator._Count number(5,0), HV209_HasRefrigerator._Sum number(4,0), HV210_HasBicycle._Count number(5,0), HV210_HasBicycle._Sum number(4,0), HV211_HasMotorbike._Count number(5,0), HV211_HasMotorbike._Sum number(4,0), HV212_HasCar._Count number(5,0), HV212_HasCar._Sum number(3,0), HV221_HasTelephone._Count number(5,0), HV221_HasTelephone._Sum number(4,0)
    -> Joiner
Joiner
    CSV_SCAN_MAX_FEATURES = 1000
    DATASET = \\129.67.26.176\map_data\DHS_Automation\Processing\HouseholdElectricity_201511\Out\All\ElectricityEtcByHousehold_All.csv
    FORMAT = CSV
    JOIN_KEYS = SurveyID SurveyID HV001_Cluster HV001_Cluster
    CSV__SCHEMA_WITH_COL_NAMES = SurveyID,number,4,0,Country,char,22,,ISO3,char,4,,Year,char,8,,_filecode,char,11,,HHID,char,6,,Spatial_LATNUM,char,1,,Spatial_LONGNUM,char,1,,Spatial_ADM1DHS,char,1,,Spatial_ADM1NAME,char,1,,Spatial_DHSREGCO,char,1,,Spatial_DHSREGNA,char,1,,Spatial_SOURCE,char,1,,Spatial_URBAN_RURA,char,1,,HV000_CCode_Phase,char,4,,HV001_Cluster,number,3,0,HV002_HHNum,number,4,0,HV005_HHSampleWeight,number,8,0,HV008_InterviewDateCMC,number,5,0,HV009_NHouseholdMembers,number,3,0,HV024_SvyRegionID,number,2,0,HV025_TypeOfResidence,number,2,0,HV201_SourceOfDrinkWater,number,3,0,HV206_HasElectricity,number,2,0,HV207_HasRadio,number,2,0,HV208_HasTelevision,number,2,0,HV209_HasRefrigerator,number,2,0,HV210_HasBicycle,number,2,0,HV211_HasMotorbike,number,2,0,HV212_HasCar,number,2,0,HV221_HasTelephone,number,2,0,HV270_WealthIndex1-5,number,2,0,HV271_WealthIndexDecimal,number,8,0
    CSV__ALLOW_SPACES_IN_COLUMN_NAMES = yes
    CSV__FIELD_NAMES_AFTER_HEADER = no
    MATCH_RULE_DISPLAY = Match First (1:0..1+)
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES SurveyID%Country%ISO3%Year%_filecode%HHID%Spatial_LATNUM%Spatial_LONGNUM%Spatial_ADM1DHS%Spatial_ADM1NAME%Spatial_DHSREGCO%Spatial_DHSREGNA%Spatial_SOURCE%Spatial_URBAN_RURA%HV000_CCode_Phase%HV001_Cluster%HV002_HHNum%HV005_HHSampleWeight%HV008_InterviewDateCMC%HV009_NHouseholdMembers%HV024_SvyRegionID%HV025_TypeOfResidence%HV201_SourceOfDrinkWater%HV206_HasElectricity%HV207_HasRadio%HV208_HasTelevision%HV209_HasRefrigerator%HV210_HasBicycle%HV211_HasMotorbike%HV212_HasCar%HV221_HasTelephone%HV270_WealthIndex1-5%HV271_WealthIndexDecimal\"%%\"Filter\"%\"STRING_ENCODED _FILTER_REGEX \"%%\"Invert Filter\"%\"CHECKBOX _FILTER_UNMATCHED yes%no\"%no"
    CSV__STRIP_QUOTES = yes
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES SurveyID%Country%ISO3%Year%_filecode%HHID%Spatial_LATNUM%Spatial_LONGNUM%Spatial_ADM1DHS%Spatial_ADM1NAME%Spatial_DHSREGCO%Spatial_DHSREGNA%Spatial_SOURCE%Spatial_URBAN_RURA%HV000_CCode_Phase%HV001_Cluster%HV002_HHNum%HV005_HHSampleWeight%HV008_InterviewDateCMC%HV009_NHouseholdMembers%HV024_SvyRegionID%HV025_TypeOfResidence%HV201_SourceOfDrinkWater%HV206_HasElectricity%HV207_HasRadio%HV208_HasTelevision%HV209_HasRefrigerator%HV210_HasBicycle%HV211_HasMotorbike%HV212_HasCar%HV221_HasTelephone%HV270_WealthIndex1-5%HV271_WealthIndexDecimal\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__GROUP_BY_DATASET = yes
    CSV__IN_FIELD_NAMES = YES
    ADDED_FIELDS = HV024_SvyRegionID
    CSV__IN_SEPARATOR = ,
    TABLE = ElectricityEtcByHousehold_All
    CSV__SKIP_LINES = 1
    CSV__SCHEMA = number,4,0,char,22,,char,4,,char,8,,char,11,,char,6,,char,1,,char,1,,char,1,,char,1,,char,1,,char,1,,char,1,,char,1,,char,4,,number,3,0,number,4,0,number,8,0,number,5,0,number,3,0,number,2,0,number,2,0,number,3,0,number,2,0,number,2,0,number,2,0,number,2,0,number,2,0,number,2,0,number,2,0,number,2,0,number,2,0,number,8,0
    CSV__SKIP_FOOTER = 0
    CSV__DUPLICATE_DELIMS = no
    JOINED -> ElectricityEtcByCluster_All_WithRegion (writer CSV_1)
ElectricityEtcByCluster_All_WithRegion (writer CSV_1)
    attributes: SurveyID auto, Country auto, ISO3 auto, Year auto, HV001_Cluster auto, HV024_SvyRegionID auto, Spatial_LATNUM auto, Spatial_LONGNUM auto, HV206_HasElectricity._Count auto, HV206_HasElectricity._Sum auto, HV207_HasRadio._Count auto, HV207_HasRadio._Sum auto, HV208_HasTelevision._Count auto, HV208_HasTelevision._Sum auto, HV209_HasRefrigerator._Count auto, HV209_HasRefrigerator._Sum auto, HV210_HasBicycle._Count auto, HV210_HasBicycle._Sum auto, HV211_HasMotorbike._Count auto, HV211_HasMotorbike._Sum auto, HV212_HasCar._Count auto, HV212_HasCar._Sum auto, HV221_HasTelephone._Count auto, HV221_HasTelephone._Sum auto
