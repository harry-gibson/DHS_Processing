FME workspace all_electric.fmw

Parameters:
- SourceDataset_CSV = \\129.67.26.176\map_data\DHS_Automation\DataExtraction\20150626_FullSiteScrape\ProcessedTables\*.RECH0.csv   # Source CSV (CommaSeparatedValue) File(s)
- FEATURE_TYPES =
- SourceDataset_CSV_3 = \\129.67.26.176\map_data\DHS_Automation\DataExtraction\20150626_FullSiteScrape\ProcessedTables\*.RECH2.csv   # Source CSV (CommaSeparatedValue) File(s)
- FEATURE_TYPES_2 =
- DestDataset_CSV = $(FME_MF_DIR)Out\All   # Destination CSV (CommaSeparatedValue) Folder
- SourceDataset_SHAPE = \\129.67.26.176\map_data\DHS_Automation\Acquisition\20150626_FullSiteScrape\downloads\**\*.shp   # Source Esri Shape File(s)
- SourceDataset_CSV_5 = C:\Users\zool1301\Documents\DHS\DHS_Info\SurveyIDs_With_Country_Details.csv   # Source CSV (CommaSeparatedValue) File(s)

Readers:
- CSV_1: CSV from $(SourceDataset_CSV_5)
- SHAPE_1: SHAPE from $(SourceDataset_SHAPE)
- CSV_2: CSV from $(SourceDataset_CSV_3)
- CSV_3: CSV from $(SourceDataset_CSV)

Writers:
- CSV_4: CSV to $(DestDataset_CSV)

337.CMGE61FL (reader SHAPE_1)
    attributes: DHSID char(254), DHSCC char(254), DHSYEAR number(16,0), DHSCLUST number(16,0), CCFIPS char(254), ADM1FIPS char(254), ADM1FIPSNA char(254), ADM1SALBNA char(254), ADM1SALBCO char(254), ADM1DHS number(16,0), ADM1NAME char(254), DHSREGCO number(16,0), DHSREGNA char(254), SOURCE char(254), URBAN_RURA char(254), LATNUM number(16,6), LONGNUM number(16,6), ALT_GPS number(16,0), ALT_DEM number(16,0), DATUM char(254)
    -> CoordinateExtractor
    -> AttributeExposer_3
CoordinateExtractor
    X_ATTR = _x
    Z_DEFAULT = -9999
    Z_ATTR = _z
    IND = 0
    Y_ATTR = _y
    -> Tester
Tester
    TEST_MODE = Automatic
    BOOL_OP = AND
    TEST_DESCRIPTION = ""
    TEST_CLAUSE:
      TEST @Evaluate(@abs(@Value(_x)-@Value(LONGNUM))<0.01) = 1
      TEST @Evaluate(@abs(@Value(_y)-@Value(LATNUM))<0.01) = 1
    PASSED -> Tester_Passed
    FAILED -> Tester_Failed
Tester_Passed: Inspector
Tester_Failed: Inspector
AttributeExposer_3
    ATTR_LIST = fme_feature_type
    -> StringSearcher_3
StringSearcher_3
    STRING_TO_SEARCH = @Value(fme_feature_type)
    MATCHED_PARTS_ATTR = _matched_parts
    CASE = no
    MATCHED_RESULT_ATTR = svyID
    REGEXP = ^\d+
    MATCHED -> AttributeKeeper_3
AttributeKeeper_3
    KEEP_ATTRS = ADM1DHS,ADM1NAME,DHSCC,DHSCLUST,DHSID,DHSREGCO,DHSREGNA,LATNUM,LONGNUM,SOURCE,svyID,URBAN_RURA
    -> BulkAttributeRenamer
BulkAttributeRenamer
    ATTRCHOICE = Selected Attributes
    PATTERN_ACTION_DISP = Add String Prefix
    ATTRLIST = ADM1DHS ADM1NAME DHSCC DHSCLUST DHSID DHSREGCO DHSREGNA LATNUM LONGNUM SOURCE URBAN_RURA
    REPLACE_STR = Spatial_
    -> FeatureMerger_2 [input 2]
Note: : *.RECH0 [CSV]
318.STIR50.RECH0 (reader CSV_3)
    attributes: HHID char(6), HV000 char(4), HV001 number(3,0), HV002 number(4,0), HV003 number(2,0), HV004 number(3,0), HV005 number(8,0), HV006 number(3,0), HV007 number(5,0), HV008 number(5,0), HV009 number(3,0), HV010 number(2,0), HV011 number(2,0), HV012 number(3,0), HV013 number(3,0), HV014 number(2,0), HV015 number(2,0), HV016 number(3,0), HV017 number(2,0), HV018 number(3,0), HV019 number(2,0), HV020 number(2,0), HV021 number(3,0), HV022 number(3,0), HV023 number(2,0), HV024 number(2,0), HV025 number(2,0), HV026 char(1), HV027 number(2,0), HV028 number(8,0),
      HV030 number(3,0), HV031 char(1), HV032 number(2,0), HV033 char(1), HV035 number(2,0), HV040 char(1), HV041 number(2,0), HV042 number(2,0), HV043 char(1), HV044 number(2,0), HV002A char(1)
    -> AttributeKeeper_2
AttributeKeeper_2
    KEEP_ATTRS = HHID,HV000,HV001,HV002,HV005,HV008,HV009,HV024,HV025
    -> AttributeExposer
AttributeExposer
    ATTR_LIST = fme_basename
    -> StringSearcher
StringSearcher
    STRING_TO_SEARCH = @Value(fme_basename)
    MATCHED_PARTS_ATTR = _parts
    CASE = no
    MATCHED_RESULT_ATTR = _filecode
    REGEXP = ^\d+\.\w+
    MATCHED -> StringSearcher_4
StringSearcher_4
    STRING_TO_SEARCH = @Value(_filecode)
    MATCHED_PARTS_ATTR = _parts
    CASE = no
    MATCHED_RESULT_ATTR = svyID
    REGEXP = ^\d+
    MATCHED -> FeatureMerger [input 1]
Note: : *.RECH2 [CSV]
230.bfir43.RECH2 (reader CSV_2)
    attributes: HHID char(6), HV201 number(3,0), HV204 number(4,0), HV205 number(3,0), HV206 number(2,0), HV207 number(2,0), HV208 number(2,0), HV209 number(2,0), HV210 number(2,0), HV211 number(2,0), HV212 number(2,0), HV213 number(3,0), HV214 char(1), HV215 char(1), HV217 number(2,0), HV218 number(2,0), HV219 number(2,0), HV220 number(3,0), HV221 number(2,0), HV225 number(2,0), HV226 number(3,0), HV227 number(2,0), HV228 number(2,0), HV230 number(2,0), HV231 number(2,0), HV232 number(2,0), HV233 number(2,0), HV234 number(4,0), HV253F char(1), HV243C number(2,0),
      HV246J char(1), HV222 char(1), HV253E char(1), HV270 number(2,0), HV234A number(2,0), HV202 char(1), HV253B number(2,0), HV237X number(2,0), HV230A number(2,0), HV237G number(2,0), HV232B number(2,0), HV237 number(2,0), HV248 char(1), HV237H char(1), HV251 char(1), HV236 char(1), HV238 number(3,0), HV246G number(3,0), HV246F number(3,0), HV247 char(1), HV253 number(2,0), HV253Z number(2,0), HV232E char(1), HV216 number(3,0), HV232Y number(2,0), HV203 char(1), HV242 number(2,0), HV237A number(2,0), HV232C char(1), HV246B char(1),
      HV253X number(2,0), HV246I char(1), HV241 number(2,0), HV239 char(1), HV240 char(1), HV237D number(2,0), HV232D char(1), HV249 char(1), HV250 char(1), HV243A number(2,0), HV253A number(2,0), HV237C number(2,0), HV252 number(2,0), HV253G char(1), HV253D char(1), HV237J char(1), HV246K char(1), HV246E number(3,0), HV246H number(3,0), HV253C number(2,0), HV237B number(2,0), HV246D number(3,0), HV230B number(2,0), HV243D number(2,0), HML2 number(2,0), HV271 number(7,0), HML1A number(2,0), HV244 number(2,0), HV237K char(1), HV246 number(2,0),
      HML1 number(2,0), HV237E number(2,0), HV235 number(2,0), HV243B number(2,0), HV237F number(2,0), HV246A number(3,0), HV237I char(1), HV246C number(2,0), HV253H char(1), HV237Z number(2,0), HV245 number(4,0)
    -> AttributeKeeper
AttributeKeeper
    KEEP_ATTRS = HHID,HV201,HV206,HV207,HV208,HV209,HV210,HV211,HV212,HV221,HV270,HV271
    -> AttributeExposer_2
AttributeExposer_2
    ATTR_LIST = fme_basename
    -> StringSearcher_2
StringSearcher_2
    STRING_TO_SEARCH = @Value(fme_basename)
    MATCHED_PARTS_ATTR = _parts
    CASE = no
    MATCHED_RESULT_ATTR = _filecode
    REGEXP = ^\d+\.\w+
    MATCHED -> FeatureMerger [input 2]
FeatureMerger
    JOIN_KEYS = @Value(_filecode) @Value(_filecode) AUTO @Value(HHID) @Value(HHID) AUTO
    MERGE_TYPE = Attributes Only
    IGNORE_NULLS = No
    ATTR_CONFLICT_RES = Use Requestor
    SUPPLIERS_FIRST = Yes
    PROCESS_DUPS = No
    ATTR_ACCUM_MODE = Merge Supplier
    NOT_MERGED -> No_RECH2_Dropped
    MERGED -> FeatureMerger_2 [input 1]
FeatureMerger_2
    JOIN_KEYS = @Value(svyID) @Value(svyID) AUTO @Value(HV001) @Value(Spatial_DHSCLUST) AUTO
    MERGE_TYPE = Attributes Only
    IGNORE_NULLS = No
    ATTR_CONFLICT_RES = Use Requestor
    SUPPLIERS_FIRST = Yes
    PROCESS_DUPS = No
    ATTR_ACCUM_MODE = Merge Supplier
    MERGED -> AttributeRenamer
    NOT_MERGED -> AttributeRenamer
AttributeRenamer
    ATTR_LIST = svyID,SurveyID,,HV001,HV001_Cluster,,HV000,HV000_CCode_Phase,,HV002,HV002_HHNum,,HV005,HV005_HHSampleWeight,,HV008,HV008_InterviewDateCMC,,HV009,HV009_NHouseholdMembers,,HV024,HV024_SvyRegionID,,HV025,HV025_TypeOfResidence,,HV201,HV201_SourceOfDrinkWater,,HV206,HV206_HasElectricity,,HV207,HV207_HasRadio,,HV208,HV208_HasTelevision,,HV209,HV209_HasRefrigerator,,HV210,HV210_HasBicycle,,HV211,HV211_HasMotorbike,,HV212,HV212_HasCar,,HV221,HV221_HasTelephone,,HV270,HV270_WealthIndex1-5,,HV271,HV271_WealthIndexDecimal,
    -> FeatureMerger_3 [input 1]
No_RECH2_Dropped: Inspector
CSV (reader CSV_1)
    attributes: Country char(33), Year char(8), Survey_ID_num number(4,0), SurveyAPI_ID char(10), Type char(4), Dataset range min char(8), Dataset range max char(7), IgnoreDupe number(2,0), DHS char(3), ISO3 char(4), ISO2 char(3), GAUL number(6,0)
    -> AttributeKeeper_4
AttributeKeeper_4
    KEEP_ATTRS = Country,ISO2,ISO3,Survey_ID_num,Type,Year
    -> FeatureMerger_3 [input 2]
FeatureMerger_3
    JOIN_KEYS = @Value(SurveyID) @Value(Survey_ID_num) AUTO
    MERGE_TYPE = Attributes Only
    IGNORE_NULLS = No
    ATTR_CONFLICT_RES = Use Requestor
    SUPPLIERS_FIRST = Yes
    PROCESS_DUPS = No
    ATTR_ACCUM_MODE = Merge Supplier
    MERGED -> ElectricityEtcByHousehold_All (writer CSV_4)
    MERGED -> NullAttributeMapper
    NOT_MERGED -> No_Survey_Details_ERROR
ElectricityEtcByHousehold_All (writer CSV_4)
    attributes: SurveyID auto, Country auto, ISO3 auto, Year auto, _filecode auto, HHID auto, Spatial_LATNUM auto, Spatial_LONGNUM auto, Spatial_ADM1DHS auto, Spatial_ADM1NAME auto, Spatial_DHSREGCO auto, Spatial_DHSREGNA auto, Spatial_SOURCE auto, Spatial_URBAN_RURA auto, HV000_CCode_Phase auto, HV001_Cluster auto, HV002_HHNum auto, HV005_HHSampleWeight auto, HV008_InterviewDateCMC auto, HV009_NHouseholdMembers auto, HV024_SvyRegionID auto, HV025_TypeOfResidence auto, HV201_SourceOfDrinkWater auto, HV206_HasElectricity auto, HV207_HasRadio auto, HV208_HasTelevision auto, HV209_HasRefrigerator auto, HV210_HasBicycle auto, HV211_HasMotorbike auto, HV212_HasCar auto,
      HV221_HasTelephone auto, HV270_WealthIndex1-5 auto, HV271_WealthIndexDecimal auto
Note: Replace anything other than 1 with zero, so we can sum them into clusters
NullAttributeMapper
    ATTRCHOICE = Selected Attributes
    NULL_TREATMENT = New Value
    NEW_VALUE = 0
    REG_EXP = [^1]
    ATTRLIST = HV206_HasElectricity HV207_HasRadio HV208_HasTelevision HV209_HasRefrigerator HV210_HasBicycle HV211_HasMotorbike HV212_HasCar HV221_HasTelephone
    SOURCE_ATTR_VAL = Empty Null
    -> StatisticsCalculator
StatisticsCalculator
    SUM_ATTR = _Sum
    PREPEND_ATTR_NAME_CHOICE = For multiple results only
    GROUP_BY = Country HV001_Cluster ISO3 Spatial_LATNUM Spatial_LONGNUM SurveyID Year HV024_SvyRegionID
    STATS_ATTRS = HV206_HasElectricity HV207_HasRadio HV208_HasTelevision HV209_HasRefrigerator HV210_HasBicycle HV211_HasMotorbike HV212_HasCar HV221_HasTelephone
    COUNT_ATTR = _Count
    COMPUTE_HISTOGRAM = NO
    SUMMARY -> ElectricityEtcByCluster_All (writer CSV_4)
ElectricityEtcByCluster_All (writer CSV_4)
    attributes: SurveyID auto, Country char(33), ISO3 char(4), Year char(8), HV001_Cluster auto, Spatial_LATNUM auto, Spatial_LONGNUM auto, HV206_HasElectricity._Count auto, HV206_HasElectricity._Sum auto, HV207_HasRadio._Count auto, HV207_HasRadio._Sum auto, HV208_HasTelevision._Count auto, HV208_HasTelevision._Sum auto, HV209_HasRefrigerator._Count auto, HV209_HasRefrigerator._Sum auto, HV210_HasBicycle._Count auto, HV210_HasBicycle._Sum auto, HV211_HasMotorbike._Count auto, HV211_HasMotorbike._Sum auto, HV212_HasCar._Count auto, HV212_HasCar._Sum auto, HV221_HasTelephone._Count auto, HV221_HasTelephone._Sum auto
No_Survey_Details_ERROR: Inspector
