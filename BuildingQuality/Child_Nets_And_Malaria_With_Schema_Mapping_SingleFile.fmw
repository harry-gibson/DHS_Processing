FME workspace Child_Nets_And_Malaria_With_Schema_Mapping_SingleFile.fmw

Parameters:
- SourceDataset_CSV = C:\Users\zool1301\Documents\DHS\DHS_Info\SurveyIDs_With_Country_Details.csv   # Source CSV (CommaSeparatedValue) File(s)
- SourceDataset_CSV_3 = \\129.67.26.176\map_data\DHS_Automation\SupportingInfo\Standard country codes Sub Saharan Africa.csv   # Source CSV (CommaSeparatedValue) File(s)
- DestDataset_CSV_2 = \\129.67.26.176\map_data\DHS_Automation\Processing\Building_Quality_Vs_Infection_PWG_LT_201512\Out\Rerun_SingleOutput   # Destination CSV (CommaSeparatedValue) Folder
- DestDataset_CSV = \\129.67.26.176\map_data\DHS_Automation\Processing\Building_Quality_Vs_Infection_PWG_LT_201512\Out\Rerun_SingleOutput   # Destination CSV (CommaSeparatedValue) Folder

Readers:
- CSV_1: CSV from $(SourceDataset_CSV)
- CSV_2: CSV from $(SourceDataset_CSV_3)

Writers:
- CSV_3: CSV to $(DestDataset_CSV_2)
- CSV_4: CSV to $(DestDataset_CSV)

Sampler_3
    GROUP_BY = !_OUTNAME
    SAMPLE_TYPE_LONG = First N Features
    RATE = 1
    SAMPLED -> AttributeRemover
Note: Write the data in the native form i.e. with coded attribute names and values
AttributeRemover
    REMOVE_ATTRS = ISO3,SURVEY_ID_NUM,SURVEYID,TYPE,YEAR
    -> AttributeExploder_2
AttributeExploder_2
    KEEP_ATTRIBUTES = No
    KEEP_GEOMETRY = No
    ATTR_VALUE_LABEL = _attr_value
    LIST_NAME = _attr_list
    ATTR_NAME_LABEL = _attr_name
    EXPLODING_TYPE = Features
    -> FeatureMerger_3 [input 2]
Note: Write the data in the native form i.e. with coded attribute names and values
File1 (writer CSV_4)
    attributes: YEAR auto, SURVEY_ID_NUM auto, TYPE auto, ISO3 char(4), SURVEYID auto, HHID auto, HVIDX auto, CHILDID auto, HV104 auto, HV105 auto, HML19 auto, HML20 auto, HML32 auto, HML33 auto, HML35 auto, HC53 auto, HC56 auto, HC57 auto
Note: The first section of this workspace(not the schema mapped part) is equivalent to the following query / SELECT / r1.surveyid, / r1.hhid, / r1.hvidx, / r1.hv104, / r1.hv105, / rm.hml19, / rm.hml20, / rm.hml32, / rm.hml33, / rm.hml35, / rc.hc53, / rc.hc56, / rc.hc57 / FROM / dhs_data_tables."RECH1" r1 / LEFT JOIN / dhs_data_tables."RECHMH" rm / ON r1.surveyid = rm.surveyid AND r1.hhid = rm.hhid AND r1.hvidx = text(rm.hmhidx) / LEFT JOIN / dhs_data_tables."RECH6" rc / ON r1.surveyid = rc.surveyid AND r1.hhid = rc.hhid AND r1.hvidx = rc.idxh6 / WHERE / -- r1.surveyid=211 AND / r1.hv105 < 18
StringSearcher
    REGEXP = ^\w+
    STRING_TO_SEARCH = @Value(name)
    MATCHED_RESULT_ATTR = _origName
    MATCHED_PARTS_ATTR = _blah
    CASE = no
    MATCHED -> Tester_5
Tester_5
    BOOL_OP = OR
    TEST_CLAUSE = TEST @Value(_origName) = @Value(name)
    TEST_MODE = Automatic
    TEST_DESCRIPTION = ""
    FAILED -> FeatureMerger_3 [input 1]
    PASSED -> UnchangedDropped
UnchangedDropped: Inspector
FeatureMerger_3
    SUPPLIERS_FIRST = No
    MERGE_TYPE = Attributes Only
    ATTR_ACCUM_MODE = Merge Supplier
    PROCESS_DUPS = No
    ATTR_CONFLICT_RES = Use Requestor
    JOIN_KEYS = @Value(_origName) @Value(_attr_name) AUTO
    IGNORE_NULLS = No
    MERGED -> AttributeKeeper_4
Note: Attach the schema info to the remapped features
FeatureMerger_2
    SUPPLIERS_FIRST = No
    MERGE_TYPE = Attributes Only
    ATTR_ACCUM_MODE = Merge Supplier
    PROCESS_DUPS = No
    ATTR_CONFLICT_RES = Use Requestor
    JOIN_KEYS = @Value(!_OUTNAME_LABELLED) @Value(!_OUTNAME_LABELLED) AUTO
    IGNORE_NULLS = No
    MERGED -> File1 (writer CSV_3)
Note: Write the data including the interpreted columns as well as the native ones
File1 (writer CSV_3)

Bookmark: Get the IDs and related info (country code) of the SSA surveys
SurveyIDs_With_Country_Details (reader CSV_1)
    attributes: Country char(33), Year char(8), Survey_ID_num number(4,0), SurveyAPI_ID char(10), Type char(4), Dataset range min char(8), Dataset range max char(7), IgnoreDupe number(2,0), DHS char(3), ISO3 char(4), ISO2 char(3), GAUL number(6,0)
    -> FeatureMerger [input 1]
Standard country codes Sub Saharan Africa (reader CSV_2)
    attributes: Shortname char(33), Official Name char(49), ISO3 char(4), ISO2 char(3), UNI number(4,0), UNDP char(4), FAOSTAT number(4,0), GAUL number(4,0), DHS char(3), SSA number(2,0)
    -> AttributeKeeper
AttributeKeeper
    KEEP_ATTRS = ISO3
    -> FeatureMerger [input 2]
FeatureMerger
    SUPPLIERS_FIRST = No
    MERGE_TYPE = Attributes Only
    ATTR_ACCUM_MODE = Merge Supplier
    PROCESS_DUPS = No
    ATTR_CONFLICT_RES = Use Requestor
    JOIN_KEYS = @Value(ISO3) @Value(ISO3) AUTO
    IGNORE_NULLS = No
    MERGED -> Sampler_2
Note: testing: just run on a few surveys
Sampler_2
    SAMPLE_TYPE_LONG = Every Nth Feature
    RATE = 1
    SAMPLED -> AttributeKeeper_2
AttributeKeeper_2
    KEEP_ATTRS = Survey_ID_num,ISO3,Type,Year
    -> FeatureReader

Bookmark: Read the RECH1 household schedule
FeatureReader
    POSTGRES_SCHEMALIST = dhs_data_tables
    ATTR_CONFLICT_RES = Use Result
    FORMAT = POSTGRES
    POSTGRES_QUERY_FEATURE_TYPES_FOR_MERGE_FILTERS = Yes
    FEATURETYPES_RADIO = FEATURETYPES
    DATASET = staging@map.zoo.ox.ac.uk:5434/dhs_data_pit
    WHERE = surveyid = @Value(Survey_ID_num) and hv105 < 18
    COMBINE_GEOM = Use Result
    ATTRIBUTES = dhs_data_tables.RECH1,"surveyid,hhid,hvidx,hv101,hv102,hv103,hv104,hv105,hv106,hv107,hv108,hv109,hv110,hv111,hv112,hv113,hv114,hv115,hv116,hv117,hv118,hv120,hv121,hv122,hv123,hv124,hv125,hv126,hv127,hv128,hv129,hv130,hv140,hv131,hv132,hv133,hv134,hv135,hv136,hv137,hv138,hv139"
    ATTR_ACCUM_MODE = Merge Initiator and Result
    OUTPUT_FEATURES_DISPLAY = Based on Connections
    POSTGRES_NAMED_CONNECTION = staging@map.zoo.ox.ac.uk:5434/dhs_data_pit
    FEATURETYPES = dhs_data_tables.RECH1
    dhs_data_tables.RECH1 -> AttributeKeeper_3
AttributeKeeper_3
    KEEP_ATTRS = hhid,ISO3,Survey_ID_num,surveyid,Type,Year,hv104,hv105,hvidx
    -> Joiner_3
Joiner_3
    PREFETCH_EXHAUSTIVE = Yes
    MATCH_RULE_DISPLAY = Must Match Exactly One (1:1)
    DATASET = staging@map.zoo.ox.ac.uk:5434/dhs_data_pit
    FORMAT = POSTGRES
    TABLE = dhs_data_tables.RECH0
    POSTGRES_QUERY_FEATURE_TYPES_FOR_MERGE_FILTERS = Yes
    POSTGRES_NAMED_CONNECTION = staging@map.zoo.ox.ac.uk:5434/dhs_data_pit
    ADDED_FIELDS = hv001 hv002
    CACHE_SIZE = 5000000
    JOIN_KEYS = hhid hhid surveyid surveyid
    JOINED -> Joiner

Bookmark: Attach the RECH6 and RECHMH data to them
Joiner
    PREFETCH_EXHAUSTIVE = Yes
    MATCH_RULE_DISPLAY = Must Match Zero or One (1:0..1)
    DATASET = staging@map.zoo.ox.ac.uk:5434/dhs_data_pit
    FORMAT = POSTGRES
    TABLE = dhs_data_tables.RECHMH
    POSTGRES_QUERY_FEATURE_TYPES_FOR_MERGE_FILTERS = Yes
    POSTGRES_NAMED_CONNECTION = staging@map.zoo.ox.ac.uk:5434/dhs_data_pit
    ADDED_FIELDS = hml19 hml20 hml32 hml33 hml35
    CACHE_SIZE = 5000000
    JOIN_KEYS = hhid hhid surveyid surveyid hvidx hmhidx
    JOINED -> Joiner_2
Joiner_2
    PREFETCH_EXHAUSTIVE = Yes
    MATCH_RULE_DISPLAY = Must Match Zero or One (1:0..1)
    DATASET = staging@map.zoo.ox.ac.uk:5434/dhs_data_pit
    FORMAT = POSTGRES
    TABLE = dhs_data_tables.RECH6
    POSTGRES_QUERY_FEATURE_TYPES_FOR_MERGE_FILTERS = Yes
    POSTGRES_NAMED_CONNECTION = staging@map.zoo.ox.ac.uk:5434/dhs_data_pit
    ADDED_FIELDS = hc53 hc56 hc57
    CACHE_SIZE = 5000000
    JOIN_KEYS = hhid hhid surveyid surveyid hvidx idxh6
    JOINED -> BulkAttributeRenamer
Note: Rename DB attributes to uppercase to match what's recorded in the CSV spec files
BulkAttributeRenamer
    CASE_CHANGE_TYPE = UPPERCASE
    ATTRCHOICE = All Attributes
    PATTERN_ACTION_DISP = Change Case
    -> NullAttributeMapper
NullAttributeMapper
    NULL_TREATMENT = Null
    SOURCE_ATTR_VAL = "Missing (Selected Attributes Only)"
    ATTRCHOICE = Selected Attributes
    ATTRLIST = HC53 HC56 HC57 HML19 HML20 HML32 HML33 HML35 HV104 HV105 HVIDX
    -> AttributeCreator
AttributeCreator
    ATTR_LIST = !_OUTNAME,ChildMalaria_All,!_OUTNAME_LABELLED,ChildMalaria_Labelled_All,CHILDID,@Value(HHID)_@Value(HVIDX)
    -> SchemaMapper
    -> File1 (writer CSV_4)
    -> Sampler_3

Bookmark: Interpret attr names / values
Note: The SchemaMappper is used as a one-stop transformer to make a copy of all coded value attributes, named to give the actual question text and containing the interpreted value descriptions, e.g. cooking fuel = "electricity" rather than "1". / (It could equally do it into the original attributes). / Value mappings are recorded in an external csv table, which was generated from the original DCF dictionary files.
SchemaMapper
    DATASET = \\129.67.26.176\map_data\DHS_Automation\DataExtraction\20150626_FullSiteScrape\SchemaMappingSupport\SchemaMapperValueSpecs_RH1-RH6-RHML_AllValues_Labelled_GenericCommonFieldNames.csv
    CSV__SKIP_LINES = 1
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    FORMAT = CSV
    IDXSOURCECOL = ""
    TABLE = SchemaMapperValueSpecs_RH1-RH6-RHML_AllValues_Labelled_GenericCommonFieldNames
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__DUPLICATE_DELIMS = no
    CSV__STRIP_QUOTES = yes
    IDXDESTCOL = ""
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__GROUP_BY_DATASET = yes
    CSV__SCHEMA = char,33,,char,8,,number,4,0,char,10,,char,4,,char,8,,char,7,,number,2,0,char,3,,char,4,,char,3,,number,6,0
    CSV__IN_SEPARATOR = ,
    IDXSOURCEATTR = fme_feature_type
    IDXDESTATTR = fme_feature_type
    MATCH_ATTRS = SurveyIdColumnNameInData SurveyID ValueFieldIn Value
    ROW_ID_ATTR = _schemamapper_row_ids
    CSV__SKIP_FOOTER = 0
    CSV__IN_FIELD_NAMES = YES
    CSV__ALLOW_SPACES_IN_COLUMN_NAMES = yes
    CSV__FIELD_NAMES_AFTER_HEADER = no
    MAP_ATTRS = """""" ValueDescFieldOut ValueDesc
    CSV_SCAN_MAX_FEATURES = 1000
    UNMAPPED -> SchemaMapper_Unmapped
    MAPPED -> SchemaMapper_2
SchemaMapper_2
    DATASET = \\129.67.26.176\map_data\DHS_Automation\DataExtraction\20150626_FullSiteScrape\SchemaMappingSupport\SchemaMapperValueSpecs_RH1-RH6-RHML_AllValues_Labelled_GenericCommonFieldNames.csv
    CSV__SKIP_LINES = 1
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    FORMAT = CSV
    IDXSOURCECOL = ""
    TABLE = SchemaMapperValueSpecs_RH1-RH6-RHML_AllValues_Labelled_GenericCommonFieldNames
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__DUPLICATE_DELIMS = no
    CSV__STRIP_QUOTES = yes
    IDXDESTCOL = ""
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__GROUP_BY_DATASET = yes
    CSV__SCHEMA = char,33,,char,8,,number,4,0,char,10,,char,4,,char,8,,char,7,,number,2,0,char,3,,char,4,,char,3,,number,6,0
    CSV__IN_SEPARATOR = ,
    IDXSOURCEATTR = fme_feature_type
    IDXDESTATTR = fme_feature_type
    MATCH_ATTRS = SurveyIdColumnNameInData SurveyID
    ROW_ID_ATTR = _schemamapper_row_ids
    CSV__SKIP_FOOTER = 0
    CSV__IN_FIELD_NAMES = YES
    CSV__ALLOW_SPACES_IN_COLUMN_NAMES = yes
    CSV__FIELD_NAMES_AFTER_HEADER = no
    MAP_ATTRS = ValueFieldIn ValueFieldOut """"""
    CSV_SCAN_MAX_FEATURES = 1000
    MAPPED -> Sampler
    MAPPED -> FeatureMerger_2 [input 1]
Tester_3
    BOOL_OP = OR
    TEST_CLAUSE = TEST @Value(name) BEGINS_WITH !_
    TEST_MODE = Automatic
    TEST_DESCRIPTION = ""
    FAILED -> StringSearcher
    PASSED -> AttributeKeeper_4
SchemaMapper_Unmapped: Inspector

Bookmark: Generate output schema info for writer
Note: Because the schema mapper generates new attribs on the fly the workbench doesn't know their names so the writer for these needs to be dynamic. This requires instructions on what the output attrib names should be: generate one copy of this for each output file
Sampler
    GROUP_BY = !_OUTNAME
    SAMPLE_TYPE_LONG = First N Features
    RATE = 1
    SAMPLED -> BulkAttributeRenamer_2
BulkAttributeRenamer_2
    REPLACE_STR = !_
    ATTRCHOICE = Selected Attributes
    ATTRLIST = ISO3 SURVEY_ID_NUM SURVEYID TYPE YEAR CHILDID
    PATTERN_ACTION_DISP = Add String Prefix
    -> AttributeExploder
    -> BulkAttributeRenamer_2_Output
AttributeExploder
    KEEP_ATTRIBUTES = Yes
    KEEP_GEOMETRY = No
    ATTR_VALUE_LABEL = _attr_value
    ATTR_NAME_LABEL = name
    EXPLODING_TYPE = Features
    -> Tester_3
AttributeKeeper_4
    KEEP_ATTRS = name,!_OUTNAME_LABELLED
    -> Sorter
Sorter
    SORT_PARM = !_OUTNAME_LABELLED ALPHA ASCENDING name ALPHA ASCENDING
    SORTED -> StringReplacer
StringReplacer
    FIND_TEXT = ^!_
    REGEXP = yes
    NO_MATCH = _FME_NO_OP_
    SRC_ATTRS = name
    CASE = no
    -> AttributeCreator_2
AttributeCreator_2
    ATTR_LIST = fme_data_type,fme_buffer
    -> Tester
Tester
    BOOL_OP = OR
    TEST_CLAUSE:
      TEST @Value(name) BEGINS_WITH fme
      TEST @Value(name) BEGINS_WITH !_
      TEST @Value(name) CONTAINS OUTNAME
    TEST_MODE = Automatic
    TEST_DESCRIPTION = ""
    FAILED -> ListBuilder
ListBuilder
    GRP_BY = !_OUTNAME_LABELLED
    LIST_NAME = attribute
    -> FeatureMerger_2 [input 2]
BulkAttributeRenamer_2_Output: Inspector
