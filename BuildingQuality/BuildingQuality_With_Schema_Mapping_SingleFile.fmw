FME workspace BuildingQuality_With_Schema_Mapping_SingleFile.fmw

Parameters:
- SourceDataset_CSV = C:\Users\zool1301\Documents\DHS\DHS_Info\SurveyIDs_With_Country_Details.csv   # Source CSV (CommaSeparatedValue) File(s)
- SourceDataset_CSV_3 = \\129.67.26.176\map_data\DHS_Automation\SupportingInfo\Standard country codes Sub Saharan Africa.csv   # Source CSV (CommaSeparatedValue) File(s)
- DestDataset_CSV_2 = \\129.67.26.176\map_data\DHS_Automation\Processing\Building_Quality_Vs_Infection_PWG_LT_201512\Out\Rerun_SingleOutput   # Destination CSV (CommaSeparatedValue) Folder
- DestDataset_CSV = \\129.67.26.176\map_data\DHS_Automation\Processing\Building_Quality_Vs_Infection_PWG_LT_201512\Out\Rerun_SingleOutput   # Destination CSV (CommaSeparatedValue) Folder

Readers:
- CSV_1: CSV from $(SourceDataset_CSV)
- CSV_2: CSV from $(SourceDataset_CSV_3)

Writers:
- CSV_3: CSV to $(DestDataset_CSV_2)
- CSV_4: CSV to $(DestDataset_CSV)

Note: The first section of this workspace(not the schema mapped part) is equivalent to the following query / SELECT / r0.surveyid, / r0.hhid, / r0.hv001, / r0.hv002, / r0.hv005, / r0.hv009, / r0.hv025, / r2.hv213, / r2.hv215, / r2.hv214, / r2.hv216, / r2.hv253, / r2.hv270, / r2.hv271, / r2.hv201, / r2.hv205, / r2.hv238, / r2.hv226, / r2.hv244, / r2.hv245, / r2.hv246 / FROM / dhs_data_tables."RECH0" r0 / INNER JOIN / dhs_data_tables."RECH2" r2 / ON / r0.surveyid = r2.surveyid / AND / r0.hhid = r2.hhid
AttributeRemover
    REMOVE_ATTRS = ISO3,SURVEY_ID_NUM,SURVEYID,TYPE,YEAR
    -> AttributeExploder_2
AttributeExploder_2
    EXPLODING_TYPE = Features
    KEEP_GEOMETRY = No
    ATTR_NAME_LABEL = _attr_name
    ATTR_VALUE_LABEL = _attr_value
    LIST_NAME = _attr_list
    KEEP_ATTRIBUTES = No
    -> FeatureMerger_3 [input 2]
Note: Write the data in the native form i.e. with coded attribute names and values
File1 (writer CSV_4)
    attributes: YEAR auto, SURVEY_ID_NUM auto, TYPE auto, ISO3 char(4), SURVEYID auto, HHID auto, HV000 auto, HV001 auto, HV002 auto, HV005 auto, HV009 auto, HV025 auto, HV201 auto, HV205 auto, HV206 auto, HV207 auto, HV208 auto, HV209 auto, HV210 auto, HV211 auto, HV212 auto, HV213 auto, HV214 auto, HV215 auto, HV216 auto, HV221 auto, HV226 auto, HV238 auto, HV243A auto, HV243B auto,
      HV243C auto, HV243D auto, HV244 auto, HV245 auto, HV246 auto, HV247 auto, HV253 auto, HV270 auto, HV271 auto
Note: Write the data including the interpreted columns as well as the native ones
File1 (writer CSV_3)

Bookmark: Get the IDs and related info (country code) of the SSA surveys
SurveyIDs_With_Country_Details (reader CSV_1)
    attributes: Country char(33), Year char(8), Survey_ID_num number(4,0), SurveyAPI_ID char(10), Type char(4), Dataset range min char(8), Dataset range max char(7), IgnoreDupe number(2,0), DHS char(3), ISO3 char(4), ISO2 char(3), GAUL number(6,0)
    -> FeatureMerger [input 1]
Standard country codes Sub Saharan Africa (reader CSV_2)
    attributes: Shortname char(33), Official Name char(49), ISO3 char(4), ISO2 char(3), UNI number(4,0), UNDP char(4), FAOSTAT number(4,0), GAUL number(4,0), DHS char(3), SSA number(2,0)
    -> AttributeKeeper
AttributeKeeper
    KEEP_ATTRS = ISO3
    -> FeatureMerger [input 2]
FeatureMerger
    MERGE_TYPE = Attributes Only
    SUPPLIERS_FIRST = No
    IGNORE_NULLS = No
    ATTR_CONFLICT_RES = Use Requestor
    ATTR_ACCUM_MODE = Merge Supplier
    JOIN_KEYS = @Value(ISO3) @Value(ISO3) AUTO
    PROCESS_DUPS = No
    MERGED -> Sampler_2
Note: testing: just run on a few surveys
Sampler_2
    SAMPLE_TYPE_LONG = Every Nth Feature
    RATE = 1
    SAMPLED -> AttributeKeeper_2
AttributeKeeper_2
    KEEP_ATTRS = Survey_ID_num,ISO3,Type,Year
    -> FeatureReader

Bookmark: Read the RECH0 household data
FeatureReader
    COMBINE_GEOM = Use Result
    FEATURETYPES_RADIO = FEATURETYPES
    POSTGRES_NAMED_CONNECTION = staging@map.zoo.ox.ac.uk:5434/dhs_data_pit
    OUTPUT_FEATURES_DISPLAY = Based on Connections
    ATTRIBUTES = dhs_data_tables.RECH0,"surveyid,hhid,hv000,hv001,hv002,hv002a,hv003,hv004,hv005,hv006,hv007,hv008,hv009,hv010,hv011,hv012,hv013,hv014,hv015,hv016,hv017,hv018,hv019,hv020,hv021,hv022,hv023,hv024,hv025,hv026,hv027,hv028,hv030,hv031,hv032,hv033,hv035,hv040,hv041,hv042,hv043,hv044"
    ATTR_CONFLICT_RES = Use Result
    POSTGRES_SCHEMALIST = dhs_data_tables
    WHERE = surveyid = @Value(Survey_ID_num)
    FEATURETYPES = dhs_data_tables.RECH0
    POSTGRES_QUERY_FEATURE_TYPES_FOR_MERGE_FILTERS = Yes
    FORMAT = POSTGRES
    ATTR_ACCUM_MODE = Merge Initiator and Result
    DATASET = staging@map.zoo.ox.ac.uk:5434/dhs_data_pit
    dhs_data_tables.RECH0 -> AttributeKeeper_3
AttributeKeeper_3
    KEEP_ATTRS = hhid,hv001,hv002,hv005,hv009,hv025,ISO3,Survey_ID_num,surveyid,Type,Year,hv000
    -> Joiner

Bookmark: Attach the RECH2 data to them
Joiner
    POSTGRES_QUERY_FEATURE_TYPES_FOR_MERGE_FILTERS = Yes
    MATCH_RULE_DISPLAY = Must Match Zero or One (1:0..1)
    PREFETCH_EXHAUSTIVE = Yes
    CACHE_SIZE = 1000000
    DATASET = staging@map.zoo.ox.ac.uk:5434/dhs_data_pit
    JOIN_KEYS = hhid hhid surveyid surveyid
    TABLE = dhs_data_tables.RECH2
    FORMAT = POSTGRES
    POSTGRES_NAMED_CONNECTION = staging@map.zoo.ox.ac.uk:5434/dhs_data_pit
    ADDED_FIELDS = hv201 hv205 hv206 hv207 hv208 hv209 hv210 hv211 hv212 hv213 hv214 hv215 hv216 hv221 hv226 hv238 hv243a hv243b hv243c hv243d hv244 hv245 hv246 hv247 hv253 hv270 hv271
    JOINED -> AttributeCreator
AttributeCreator
    ATTR_LIST = !_outname,All_BuildingQuality,!_outname_labelled,All_BuildingQuality_Labelled
    -> BulkAttributeRenamer
Note: Rename DB attributes to uppercase to match what's recorded in the CSV spec files
BulkAttributeRenamer
    ATTRCHOICE = All Attributes
    CASE_CHANGE_TYPE = UPPERCASE
    PATTERN_ACTION_DISP = Change Case
    -> File1 (writer CSV_4)
    -> SchemaMapper
    -> Sampler_3
Sampler_3
    SAMPLE_TYPE_LONG = First N Features
    RATE = 1
    GROUP_BY = !_OUTNAME
    SAMPLED -> AttributeRemover

Bookmark: Interpret attr names / values
Note: This SchemaMappper is used as a one-stop transformer to make a copy of all coded value attributes, named to include the actual question text and containing the interpreted value descriptions, e.g. cooking fuel = "electricity" rather than "1". / (It could equally do it into the original attributes). / Value mappings are recorded in an external csv table, which was generated from the original DCF dictionary files.
SchemaMapper
    CSV__IN_FIELD_NAMES = YES
    CSV__DUPLICATE_DELIMS = no
    CSV__STRIP_QUOTES = yes
    CSV__SKIP_LINES = 1
    IDXDESTCOL = ""
    CSV__IN_SEPARATOR = ,
    CSV__SKIP_FOOTER = 0
    IDXSOURCEATTR = fme_feature_type
    CSV__FIELD_NAMES_AFTER_HEADER = no
    CSV__GROUP_BY_DATASET = yes
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    IDXSOURCECOL = ""
    CSV_SCAN_MAX_FEATURES = 1000
    DATASET = \\129.67.26.176\map_data\DHS_Automation\DataExtraction\20150626_FullSiteScrape\SchemaMappingSupport\SchemaMapperValueSpecs_RH1-RH6-RHML_AllValues_Labelled_GenericCommonFieldNames.csv
    CSV__SCHEMA = char,33,,char,8,,number,4,0,char,10,,char,4,,char,8,,char,7,,number,2,0,char,3,,char,4,,char,3,,number,6,0
    CSV__ALLOW_SPACES_IN_COLUMN_NAMES = yes
    MATCH_ATTRS = SurveyIdColumnNameInData SurveyID ValueFieldIn Value
    IDXDESTATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    TABLE = SchemaMapperValueSpecs_RH1-RH6-RHML_AllValues_Labelled_GenericCommonFieldNames
    FORMAT = CSV
    MAP_ATTRS = """""" ValueDescFieldOut ValueDesc
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    ROW_ID_ATTR = _schemamapper_row_ids
    UNMAPPED -> SchemaMapper_MappingNotFound
    MAPPED -> SchemaMapper_2
Note: This SchemaMapper is used to rename the original (numeric) valued attributes, to suffix the actual question text separated from the var name by " = "
SchemaMapper_2
    CSV__IN_FIELD_NAMES = YES
    CSV__DUPLICATE_DELIMS = no
    CSV__STRIP_QUOTES = yes
    CSV__SKIP_LINES = 1
    IDXDESTCOL = ""
    CSV__IN_SEPARATOR = ,
    CSV__SKIP_FOOTER = 0
    IDXSOURCEATTR = fme_feature_type
    CSV__FIELD_NAMES_AFTER_HEADER = no
    CSV__GROUP_BY_DATASET = yes
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    IDXSOURCECOL = ""
    CSV_SCAN_MAX_FEATURES = 1000
    DATASET = \\129.67.26.176\map_data\DHS_Automation\DataExtraction\20150626_FullSiteScrape\SchemaMappingSupport\SchemaMapperValueSpecs_RH1-RH6-RHML_AllValues_Labelled_GenericCommonFieldNames.csv
    CSV__SCHEMA = char,33,,char,8,,number,4,0,char,10,,char,4,,char,8,,char,7,,number,2,0,char,3,,char,4,,char,3,,number,6,0
    CSV__ALLOW_SPACES_IN_COLUMN_NAMES = yes
    MATCH_ATTRS = SurveyIdColumnNameInData SurveyID
    IDXDESTATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    TABLE = SchemaMapperValueSpecs_RH1-RH6-RHML_AllValues_Labelled_GenericCommonFieldNames
    FORMAT = CSV
    MAP_ATTRS = ValueFieldIn ValueFieldOut """"""
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    ROW_ID_ATTR = _schemamapper_row_ids
    UNMAPPED -> SchemaMapper_2_Unmapped
    MAPPED -> FeatureMerger_2 [input 1]
    MAPPED -> Sampler
SchemaMapper_2_Unmapped: Inspector
Note: Attach the schema info to the remapped features
FeatureMerger_2
    MERGE_TYPE = Attributes Only
    SUPPLIERS_FIRST = No
    IGNORE_NULLS = No
    ATTR_CONFLICT_RES = Use Requestor
    ATTR_ACCUM_MODE = Merge Supplier
    JOIN_KEYS = @Value(!_OUTNAME_LABELLED) @Value(!_OUTNAME_LABELLED) AUTO
    PROCESS_DUPS = No
    MERGED -> File1 (writer CSV_3)
SchemaMapper_MappingNotFound: Inspector

Bookmark: Generate output schema info for writer
Note: Because the schema mapper generates new attributes on the fly the workbench doesn't know their names so the writer for these needs to be dynamic. This requires instructions on what the output attribute names should be: generate one copy of this for each output file
Note: Get one per survey
Sampler
    SAMPLE_TYPE_LONG = First N Features
    RATE = 1
    GROUP_BY = !_OUTNAME
    SAMPLED -> BulkAttributeRenamer_2
Note: Add a prefix to survey id attribs
BulkAttributeRenamer_2
    ATTRCHOICE = Selected Attributes
    ATTRLIST = ISO3 SURVEY_ID_NUM SURVEYID TYPE YEAR
    REPLACE_STR = !_
    PATTERN_ACTION_DISP = Add String Prefix
    -> AttributeExploder
AttributeExploder
    EXPLODING_TYPE = Features
    KEEP_GEOMETRY = No
    ATTR_NAME_LABEL = name
    ATTR_VALUE_LABEL = _attr_value
    KEEP_ATTRIBUTES = Yes
    -> Tester_3
Note: Separate out survey id attribs
Tester_3
    BOOL_OP = OR
    TEST_CLAUSE = TEST @Value(name) BEGINS_WITH !_
    TEST_MODE = Automatic
    TEST_DESCRIPTION = ""
    PASSED -> AttributeKeeper_4
    FAILED -> StringSearcher
Note: Fiind the original variable name, without the question text added by the schemamappers
StringSearcher
    REGEXP = ^\w+
    STRING_TO_SEARCH = @Value(name)
    MATCHED_RESULT_ATTR = _origName
    CASE = no
    MATCHED_PARTS_ATTR = _blah
    MATCHED -> Tester_5
Note: Drop the original (unrenamed) copies
Tester_5
    BOOL_OP = OR
    TEST_CLAUSE = TEST @Value(_origName) = @Value(name)
    TEST_MODE = Automatic
    TEST_DESCRIPTION = ""
    FAILED -> FeatureMerger_3 [input 1]
Note: The second schemamapper creates an attribute for everything in the mapping, not just what's required / in the data. Use the attributes from before the schemamapper to select the renamed attributes that should be kept (written to the output)
FeatureMerger_3
    MERGE_TYPE = Attributes Only
    SUPPLIERS_FIRST = No
    IGNORE_NULLS = No
    ATTR_CONFLICT_RES = Use Requestor
    ATTR_ACCUM_MODE = Merge Supplier
    JOIN_KEYS = @Value(_origName) @Value(_attr_name) AUTO
    PROCESS_DUPS = No
    MERGED -> AttributeKeeper_4
AttributeKeeper_4
    KEEP_ATTRS = name,!_OUTNAME_LABELLED
    -> Sorter
Note: Sort, using the !_ prefix to ensure that the survey id attributes go before the data attributes.
Sorter
    SORT_PARM = !_OUTNAME_LABELLED ALPHA ASCENDING name ALPHA ASCENDING
    SORTED -> StringReplacer
StringReplacer
    NO_MATCH = _FME_NO_OP_
    REGEXP = yes
    FIND_TEXT = ^!_
    CASE = no
    SRC_ATTRS = name
    -> AttributeCreator_2
Note: set the data type for all attributes to be fme_buffer (equiv to text)
AttributeCreator_2
    ATTR_LIST = fme_data_type,fme_buffer
    -> Tester
Note: Don't keep the outname attribute as one to be written in itself
Tester
    BOOL_OP = OR
    TEST_CLAUSE:
      TEST @Value(name) BEGINS_WITH fme
      TEST @Value(name) BEGINS_WITH !_
      TEST @Value(name) CONTAINS OUTNAME
    TEST_MODE = Automatic
    TEST_DESCRIPTION = ""
    FAILED -> ListBuilder
Note: create the attribute{} list for the dynamic writer
ListBuilder
    GRP_BY = !_OUTNAME_LABELLED
    LIST_NAME = attribute
    -> FeatureMerger_2 [input 2]
