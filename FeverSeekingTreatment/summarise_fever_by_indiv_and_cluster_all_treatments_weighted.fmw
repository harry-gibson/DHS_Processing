FME workspace summarise_fever_by_indiv_and_cluster_all_treatments_weighted.fmw

Parameters:
- REC21_CSV = \\129.67.26.176\map_data\DHS_Automation\DataExtraction\20150626_FullSiteScrape\ProcessedTables\36.YEIR21.REC21.csv   # Survey CSV for REC21
- REC43_CSV = \\129.67.26.176\map_data\DHS_Automation\DataExtraction\20150626_FullSiteScrape\ProcessedTables\36.YEIR21.REC43.csv   # Survey CSV for REC43
- REC01_CSV = \\129.67.26.176\map_data\DHS_Automation\DataExtraction\20150626_FullSiteScrape\ProcessedTables\36.YEIR21.REC01.csv   # Survey CSV for REC01
- MaxAge = 5   # Children less than age (yrs)
- SurveyRecordSpec = \\129.67.26.176\map_data\DHS_Automation\DataExtraction\20150626_FullSiteScrape\ParsedSpecs\36.YEIR21.FlatRecordSpec.csv   # Record spec file for survey (Generated with python script)
- H32_UseFields_CSV = \\129.67.26.176\map_data\DHS_Automation\Processing\FeverSeekingTreatment_201507\Info\MergedH32_AllEndemic_KB.csv   # CSV specifying which H32 fields should be used
- DestDataset_FILEGDB = \\129.67.26.176\map_data\DHS_Automation\Processing\FeverSeekingTreatment_201507\Results\Weighting\All_Weighted.gdb   # Destination Geodatabase for geographic (point and region) data
- AllPointShapes = N/A   # Survey point shapefile (use N/A if none)
- OutCSVDir = \\129.67.26.176\map_data\DHS_Automation\Processing\FeverSeekingTreatment_201507\Results\Weighting   # Destination CSV Folder for tablular results
- Source_GDB_Boundaries = \\129.67.26.176\map_data\DHS_Automation\SupportingInfo\DHS_Boundary_Data\full_download\sdr_subnational_boundaries_all_surveys.gdb   # Source Geodatabase containing survey boundaries
- Use_ARI = 0   # Use ARI fields (H31*) in addition to H22
- DestDataset_GEODATABASE_FILE = \\129.67.26.176\map_data\DHS_Automation\Processing\FeverSeekingTreatment_201507\Results\Weighting\All_Weighted.gdb   # Destination Esri File Geodatabase

Readers:
- CSV_1: CSV from $(REC21_CSV)
- CSV_2: CSV from $(REC43_CSV)
- CSV_3: CSV from $(REC01_CSV)
- CSV_4: CSV from $(SurveyRecordSpec)
- CSV_5: CSV from $(H32_UseFields_CSV)
- SHAPE_1: SHAPE from $(AllPointShapes)
- GEODATABASE_FILE_1: GEODATABASE_FILE from $(Source_GDB_Boundaries)

Writers:
- FILEGDB_1: FILEGDB to $(DestDataset_FILEGDB)
- CSV_6: CSV to $(OutCSVDir)
- GEODATABASE_FILE_2: GEODATABASE_FILE to $(DestDataset_GEODATABASE_FILE)

Intermediate_By_Woman (writer CSV_6) [off]
    attributes: V000 auto, V024 auto, V012 auto, CASEID auto, V001 auto, V002 auto, V005 auto, V007 auto, total_young_count auto, fever_full_treat_young_count auto, fever_any_treat_young_count auto, fever_young_count auto, total_children_count auto
Creator
    GEOMTYPE = Geometry Object
    NUM = 1
    CREATED -> FileExistenceChecker
FileExistenceChecker
    Input = $(AllPointShapes)
    Exists -> FeatureReader
FeatureReader
    SHAPE_ENCODING = SYSTEM
    INTERACT = <No Spatial Filter>
    COMBINE_GEOM = Use Result
    SHAPE_CLIP_TO_ENVELOPE = NO
    FEATURETYPES_RADIO = FEATURETYPES
    DATASET = $(AllPointShapes)
    ATTRS_TO_EXPOSE = DHSCLUST
    SHAPE_USE_SEARCH_ENVELOPE = NO
    SHAPE_SIMPLE_DONUT_GEOMETRY = simple
    OUTPUT_FEATURES_DISPLAY = Based on Connections
    SHAPE_UPPER_CASE_ATTR_NAMES = No
    ATTR_ACCUM_MODE = Only Use Result
    FORMAT = SHAPE
    <SCHEMA> -> FeatureClass1 (writer GEODATABASE_FILE_2)
    <OTHER> -> FeatureMerger_2 [input 1]
    <SCHEMA> -> FeatureClass1 (writer FILEGDB_1)
FeatureClass1 (writer GEODATABASE_FILE_2)
    attributes: filecode char(12), total_children_ClusterCount double, total_young_ClusterCount double, fever_occurrence_ClusterCount double, fever_full_treat_ClusterCount double, fever_any_treat_ClusterCount double, fever_occurrence_ClusterProp double(20,10), fever_full_treat_ClusterProp double(20,10), young_full_treat_ClusterProp double(20,10), fever_any_treat_ClusterProp double(20,10), young_any_treat_ClusterProp double(20,10)
FeatureClass1 (writer FILEGDB_1)
    attributes: filecode text(12), total_children_ClusterCount double, total_young_ClusterCount double, fever_occurrence_ClusterCount double, fever_full_treat_ClusterCount double, fever_any_treat_ClusterCount double, fever_occurrence_ClusterProp double, fever_full_treat_ClusterProp double, young_full_treat_ClusterProp double, fever_any_treat_ClusterProp double, young_any_treat_ClusterProp double

Bookmark: Parse record 01 - individual (woman) respondent
Note: CSV: REC01 [CSV]
CSV (reader CSV_3)
    attributes: V026 number(2,0), V029 number(2,0), V030 number(3,0), V031 number(3,0), V000 char(4), V034 number(2,0), V040 number(3,0), V042 number(2,0), V044 char(1), V032 number(2,0), V028 number(4,0), V027 number(2,0), V025 number(2,0), V024 number(2,0), V023 number(3,0), V022 number(3,0), V021 number(3,0), V020 number(2,0), V019A number(2,0), V019 number(3,0), V018 number(3,0), V017 number(5,0), V016 number(3,0), V015 number(2,0), V014 number(2,0), V012 number(3,0), V013 number(2,0), CASEID char(9), V001 number(3,0), V002 number(4,0),
      V003 number(3,0), V004 number(3,0), V005 number(7,0), V006 number(3,0), V007 number(5,0), V008 number(5,0), V009 number(3,0), V010 number(5,0), V011 number(5,0)
    -> AttributeKeeper
Note: keep on ly the variables we're interested in
AttributeKeeper
    KEEP_ATTRS = CASEID,V000,V001,V002,V007,V012,V024,V005
    -> REC01
    -> AttributeCreator_4
Note: Convert sample weight (V005) back to decimal
AttributeCreator_4
    ATTR_LIST = V005,@Evaluate(@Value(V005)/1000000.0)
    -> FeatureMerger [input 1]
REC01: Inspector [off]

Bookmark: Parse record 21 - individual children
Note: CSV: REC21 [CSV]
CSV (reader CSV_1)
    attributes: B3 number(5,0), B2 number(5,0), B1 number(3,0), B0 number(2,0), BORD number(2,0), CASEID char(9), B16 number(3,0), BIDX number(2,0), B15 number(2,0), B13 number(2,0), B12 number(4,0), B11 number(4,0), B10 number(2,0), B9 number(2,0), B8 number(3,0), B7 number(4,0), B6 number(4,0), B5 number(2,0), B4 number(2,0)
    -> REC21
    -> AttributeKeeper_2
AttributeKeeper_2
    KEEP_ATTRS = B5,B8,BIDX,BORD,CASEID
    -> Tester
Note: Child is alive?
Tester
    BOOL_OP = OR
    TEST_MODE = Automatic
    TEST_CLAUSE = TEST @Value(B5) = 1
    TEST_DESCRIPTION = ""
    PASSED -> StatisticsCalculator_3
    PASSED -> Tester_4
Note: count total live kids (Any age) / by woman
StatisticsCalculator_3
    STATS_ATTRS = CASEID
    COMPUTE_HISTOGRAM = NO
    COUNT_ATTR = total_children_count
    PREPEND_ATTR_NAME_CHOICE = For multiple results only
    GROUP_BY = CASEID
    SUMMARY -> FeatureMerger [input 2]
Note: Child is less than / specified age?
Tester_4
    BOOL_OP = OR
    TEST_MODE = Automatic
    TEST_CLAUSE = TEST @Value(B8) < $(MaxAge)
    TEST_DESCRIPTION = ""
    PASSED -> StatisticsCalculator_5
    PASSED -> AttributeKeeper_4
Note: count total live young kids / by woman
StatisticsCalculator_5
    STATS_ATTRS = CASEID
    COMPUTE_HISTOGRAM = NO
    COUNT_ATTR = total_young_count
    PREPEND_ATTR_NAME_CHOICE = For multiple results only
    GROUP_BY = CASEID
    SUMMARY -> FeatureMerger [input 2]
AttributeKeeper_4
    KEEP_ATTRS = BIDX,CASEID
    -> FeatureMerger_3 [input 2]
REC21: Inspector [off]

Bookmark: Parse record 43 - illness incidents in children
Note: REC43: / Individual child health record
CSV (reader CSV_2)
    attributes: H12B number(2,0), H12C number(2,0), H12D number(2,0), H12E number(2,0), H12F number(2,0), H12G number(2,0), H12H number(2,0), H12I number(2,0), H12J number(2,0), H12K number(2,0), H12L number(2,0), H12M number(2,0), H12N number(2,0), H12O number(2,0), H12P number(2,0), H12Q char(1), H12R char(1), H12S number(2,0), H12T number(2,0), H12U number(2,0), H12V number(2,0), H12W char(1), H12X number(2,0), H12Y number(2,0), H12Z number(2,0), H13 number(2,0), H13B char(1), H14 number(2,0), H15 char(1), H15A char(1),
      H15B char(1), H15C char(1), H15D char(1), H15E char(1), H15F char(1), H15G char(1), H15H char(1), H15I char(1), H15J char(1), H15K char(1), H15L char(1), H15M char(1), H20 char(1), H21A char(1), H21 char(1), H22 number(2,0), H31 number(2,0), H31B number(2,0), H31C number(2,0), H31D number(2,0), H31E number(2,0), H32A number(2,0), H32B number(2,0), H32C number(2,0), H32D number(2,0), H32E number(2,0), H32F number(2,0), H32G number(2,0), H32H number(2,0), H32I number(2,0),
      H32J number(2,0), H32K number(2,0), H32L number(2,0), H32M number(2,0), H32N number(2,0), H32O number(2,0), H32P number(2,0), H32Q char(1), H32R char(1), H32S number(2,0), H32T number(2,0), H32U number(2,0), H32V number(2,0), H32W number(2,0), H32X number(2,0), H32Y number(2,0), H32Z number(2,0), H33 number(2,0), H33D number(3,0), H33M number(3,0), H33Y number(5,0), H34 number(2,0), H35 char(1), H36A number(2,0), H36B number(2,0), H36D number(2,0), H36E char(1), H36F char(1), H37A number(2,0), H37B number(2,0),
      H37C char(1), H37D number(2,0), H37E number(2,0), H37F char(1), H37G char(1), H37H number(2,0), H37I number(2,0), H37J number(2,0), H37K number(2,0), H37L number(2,0), H37M number(2,0), H37N number(2,0), H37O number(2,0), H37P number(2,0), H37X number(2,0), H37Y number(2,0), H37Z number(2,0), H38 number(2,0), H39 number(2,0), H40 char(1), H40D char(1), H40M char(1), H40Y char(1), H41A char(1), H41B char(1), H42 number(2,0), H43 number(2,0), H44A char(1), H44B char(1), H44C char(1),
      H45 char(1), H46A number(3,0), H46B char(1), H47 char(1), H5 number(2,0), HIDX number(2,0), H1 number(2,0), H2 number(2,0), H8D number(3,0), H2D number(3,0), H2M number(3,0), H2Y number(5,0), H3 number(2,0), H3D number(3,0), H3M number(3,0), H3Y number(5,0), H4 number(2,0), H4D number(3,0), H4M number(3,0), H4Y number(5,0), H12A number(2,0), H5D number(3,0), H5M number(3,0), H5Y number(5,0), H6 number(2,0), H6D number(3,0), H6M number(3,0), H6Y number(5,0), H7 number(2,0), H7D number(3,0),
      H7M number(3,0), H7Y number(5,0), H8 number(2,0), H0 number(2,0), H9Y number(5,0), H9M number(3,0), H9D number(3,0), H9 number(2,0), H8Y number(5,0), H8M number(3,0), H36C number(2,0), CASEID char(9), H0D number(2,0), H0M number(3,0), H0Y number(5,0), H10 number(2,0), H11 number(2,0), H11B number(2,0)
    -> REC43
    -> AttributeKeeper_3
AttributeKeeper_3
    KEEP_ATTRS = CASEID,H22,H31,H31B,H31C,H32A,H32B,H32C,H32D,H32E,H32F,H32G,H32H,H32I,H32J,H32K,H32L,H32M,H32N,H32O,H32P,H32Q,H32R,H32S,H32T,H32U,H32V,H32W,H32X,H32Y,H32Z,HIDX
    -> Tester_2
Note: Had fever in last 2 weeks / OR / Had cough AND short breaths AND probs in chest
Note: Currently only checking H22 as all surveys were found to cover it
Tester_2
    BOOL_OP = COMPOSITE
    TEST_MODE = Automatic
    TEST_CLAUSE:
      TEST @Value(H22) = 1
      TEST @Value(H31) BETWEEN 1,7
      TEST @Value(H31B) BETWEEN 1,7
      TEST @Value(H31C) BETWEEN 1,7
      TEST $(Use_ARI) = 1
    COMPOSITE_TEST = "1 OR (5 AND 2 AND (3 OR 4))"
    TEST_DESCRIPTION = ""
    PASSED -> FeatureMerger_3 [input 1]
Note: ensure that illness record pertains / to a child below specified age (which it will / if age=5 but may not if age < 5)
FeatureMerger_3
    ATTR_ACCUM_MODE = Merge Supplier
    MERGE_TYPE = Attributes Only
    IGNORE_NULLS = No
    ATTR_CONFLICT_RES = Use Requestor
    JOIN_KEYS = @Value(CASEID) @Value(CASEID) AUTO @Value(HIDX) @Value(BIDX) AUTO
    SUPPLIERS_FIRST = No
    PROCESS_DUPS = No
    MERGED -> StatisticsCalculator
    MERGED -> AttributeExploder
    NOT_MERGED -> IllnessRecordsChildTooOld
Note: count total ill kids by woman
StatisticsCalculator
    STATS_ATTRS = CASEID
    COMPUTE_HISTOGRAM = NO
    COUNT_ATTR = fever_young_count
    PREPEND_ATTR_NAME_CHOICE = For multiple results only
    GROUP_BY = CASEID
    SUMMARY -> FeatureMerger [input 2]
Note: Separate each illness record into a new feature / (record) for each of the variables (fields) that / can define the treatment. i.e. normalise it
AttributeExploder
    ATTR_NAME_LABEL = _attr_name
    KEEP_ATTRIBUTES = Yes
    ATTR_VALUE_LABEL = _attr_value
    KEEP_GEOMETRY = No
    EXPLODING_TYPE = Features
    -> Tester_6
IllnessRecordsChildTooOld: Inspector
REC43: Inspector [off]

Bookmark: Work out which of the H32* variables we want to look at to define treatment
Note: Keep if it's 1 (that treatment method was / set) in this illness record
Tester_6
    BOOL_OP = OR
    TEST_MODE = Automatic
    TEST_CLAUSE = TEST @Value(_attr_value) = 1
    TEST_DESCRIPTION = ""
    PASSED -> FeatureMerger_4 [input 1]
    PASSED -> FeatureMerger_8 [input 1]
Note: RecordSpec for the overall survey, / gives the survey-specific labels allocated to each H32* variable
CSV (reader CSV_4)
    attributes: FileCode char(7), RecordName char(6), RecordTypeValue char(4), Name char(6), Label char(65), Start number(4,0), Len number(3,0), Occurrences char(1), FMETYPE char(13)
    -> VariableSetter
VariableSetter
    VALUE = @Value(FileCode)
    SCOPE = Global
    VARNAME = currentFileCode
    -> Sampler_2
FeatureMerger_4
    ATTR_ACCUM_MODE = Merge Supplier
    MERGE_TYPE = Attributes Only
    IGNORE_NULLS = No
    ATTR_CONFLICT_RES = Use Requestor
    JOIN_KEYS = @Value(_attr_name) @Value(Name) AUTO
    SUPPLIERS_FIRST = No
    PROCESS_DUPS = No
    MERGED -> Sampler
Note: take the first one we find (they all / have all fields of the original / unexploded feature too)
Sampler
    SAMPLE_TYPE_LONG = First N Features
    RATE = 1
    GROUP_BY = CASEID BIDX
    SAMPLED -> AttributeRemover
Note: Remove the crud and that's our filtered output for this sickness record
AttributeRemover
    REMOVE_ATTRS = _attr_name,_attr_value
    -> StatisticsCalculator_6
Note: count total ill kids who went to / selected treatment, by woman
StatisticsCalculator_6
    STATS_ATTRS = CASEID
    COMPUTE_HISTOGRAM = NO
    COUNT_ATTR = fever_full_treat_young_count
    PREPEND_ATTR_NAME_CHOICE = For multiple results only
    GROUP_BY = CASEID
    SUMMARY -> FeatureMerger [input 2]
FeatureMerger_8
    ATTR_ACCUM_MODE = Merge Supplier
    MERGE_TYPE = Attributes Only
    IGNORE_NULLS = No
    ATTR_CONFLICT_RES = Use Requestor
    JOIN_KEYS = @Value(_attr_name) @Value(Name) AUTO
    SUPPLIERS_FIRST = No
    PROCESS_DUPS = No
    MERGED -> Sampler_3
Note: take the first one we find (they all / have all fields of the original / unexploded feature too)
Sampler_3
    SAMPLE_TYPE_LONG = First N Features
    RATE = 1
    GROUP_BY = CASEID BIDX
    SAMPLED -> AttributeRemover_2
Note: Remove the crud and that's our filtered output for this sickness record
AttributeRemover_2
    REMOVE_ATTRS = _attr_name,_attr_value
    -> StatisticsCalculator_7
Note: count total ill kids who went to / selected treatment, by woman
StatisticsCalculator_7
    STATS_ATTRS = CASEID
    COMPUTE_HISTOGRAM = NO
    COUNT_ATTR = fever_any_treat_young_count
    PREPEND_ATTR_NAME_CHOICE = For multiple results only
    GROUP_BY = CASEID
    SUMMARY -> FeatureMerger [input 2]

Bookmark: Allocate H32 manually
Sampler_2
    SAMPLE_TYPE_LONG = First N Features
    RATE = 1
    GROUP_BY = FileCode
    SAMPLED -> FeatureMerger_5 [input 2]
Note: File specifyting whether each H32* variable should or should not be used
CSV (reader CSV_5)
    attributes: FileCode char(11), RecordName char(6), RecordTypeValue char(4), Name char(5), Label char(74), Start number(4,0), Len number(2,0), Occurrences char(1), FMETYPE char(12), Note char(1), CountAsTreatmentGuess char(4), AnyTreatmentGuess char(4), Any_Treat char(2), OUTPUT_CountAsTreatmentSought char(2)
    -> FeatureMerger_5 [input 1]
Note: Get the ones relating to this survey
FeatureMerger_5
    ATTR_ACCUM_MODE = Merge Supplier
    MERGE_TYPE = Attributes Only
    IGNORE_NULLS = No
    ATTR_CONFLICT_RES = Use Requestor
    JOIN_KEYS = @Value(FileCode) @Value(FileCode) AUTO
    SUPPLIERS_FIRST = Yes
    PROCESS_DUPS = No
    MERGED -> Tester_7
    MERGED -> Tester_8
Note: Was it flagged as to-use as a proper treatment
Tester_7
    BOOL_OP = OR
    TEST_MODE = Automatic
    TEST_CLAUSE = TEST @LowerCase(@Value(OUTPUT_CountAsTreatmentSought)) = y
    TEST_DESCRIPTION = ""
    PASSED -> AttributeKeeper_5
Note: Simplify, keep only the name of attributes / that we want to keep (And test)
Note: For each attribute that was set, of each sickness / record, see if it is an attribute we are / interested in
Note: For each attribute that was set, of each sickness / record, see if it is an attribute we are / interested in
AttributeKeeper_5
    KEEP_ATTRS = Name
    -> FeatureMerger_4 [input 2]
Note: Was it flagged as to-use as any treatment
Tester_8
    BOOL_OP = OR
    TEST_MODE = Automatic
    TEST_CLAUSE = TEST @LowerCase(@Value(Any_Treat)) = y
    TEST_DESCRIPTION = ""
    PASSED -> AttributeKeeper_6
Note: Simplify, keep only the name of attributes / that we want to keep (And test)
AttributeKeeper_6
    KEEP_ATTRS = Name
    -> FeatureMerger_8 [input 2]

Bookmark: Accumulate results by individual woman
Note: Attach each of the different child summaries to each woman. / Each has a different variable name so we allow multiple suppliers to attach them all
FeatureMerger
    ATTR_ACCUM_MODE = Merge Supplier
    MERGE_TYPE = Attributes Only
    IGNORE_NULLS = No
    ATTR_CONFLICT_RES = Use Requestor
    GEOM_TYPE = Build Polygons
    JOIN_KEYS = @Value(CASEID) @Value(CASEID) AUTO
    SUPPLIERS_FIRST = No
    PROCESS_DUPS = Yes
    MERGED -> Tester_5
Tester_5
    BOOL_OP = OR
    TEST_MODE = Automatic
    TEST_CLAUSE = TEST @Value(V005) = 0
    TEST_DESCRIPTION = ""
    FAILED -> AttributeCreator
    FAILED -> Tester_3
    FAILED -> NullAttributeMapper
    PASSED -> Logger
Logger
    MESSAGE = Dropped FeatureWith Zero Weight!
    MAXFEATS = 20
    MAXCOORDS = 20
Note: Replace missing / null attribs with zero; they do not cause any error but generate loads of warnings
NullAttributeMapper
    ATTRLIST = fever_any_treat_young_count fever_full_treat_young_count fever_young_count total_children_count total_young_count
    NULL_TREATMENT = New Value
    SOURCE_ATTR_VAL = Null "Missing (Selected Attributes Only)"
    NEW_VALUE = 0
    ATTRCHOICE = Selected Attributes
    -> AttributeCreator_5
    -> Intermediate_By_Woman (writer CSV_6) [off]
Note: Apply weights!
AttributeCreator_5
    ATTR_LIST = fever_any_treat_young_count,@Evaluate(@Value(fever_any_treat_young_count)*@Value(V005)),fever_full_treat_young_count,@Evaluate(@Value(fever_full_treat_young_count)*@Value(V005)),fever_young_count,@Evaluate(@Value(fever_young_count)*@Value(V005)),total_children_count,@Evaluate(@Value(total_children_count)*@Value(V005)),total_young_count,@Evaluate(@Value(total_young_count)*@Value(V005))
    -> StatisticsCalculator_2
    -> StatisticsCalculator_4

Bookmark: Accumulate and summarise by cluster (point location)
Note: summarise by cluster (V001), also grouping by country (V000) and region (V024) so that these carry thru
StatisticsCalculator_4
    STATS_ATTRS = fever_young_count total_children_count total_young_count fever_any_treat_young_count fever_full_treat_young_count
    COMPUTE_HISTOGRAM = NO
    SUM_ATTR = _sum
    PREPEND_ATTR_NAME_CHOICE = For multiple results only
    GROUP_BY = V000 V001 V024
    SUMMARY -> AttributeCreator_2
Note: Calculate proportional results from sums
AttributeCreator_2
    ATTR_LIST = fever_occurrence_ClusterProp,@Evaluate(@Value(fever_young_count._sum)/@Value(total_young_count._sum)),young_any_treat_ClusterProp,@Evaluate(@Value(fever_any_treat_young_count._sum)/@Value(total_young_count._sum)),young_full_treat_ClusterProp,@Evaluate(@Value(fever_full_treat_young_count._sum)/@Value(total_young_count._sum)),fever_any_treat_ClusterProp,@Evaluate(@Value(fever_any_treat_young_count._sum)/@Value(fever_young_count._sum)),fever_full_treat_ClusterProp,@Evaluate(@Value(fever_full_treat_young_count._sum)/@Value(fever_young_count._sum))
    -> AttributeRenamer
AttributeRenamer
    ATTR_LIST = fever_any_treat_young_count._sum,fever_any_treat_ClusterCount,,fever_young_count._sum,fever_occurrence_ClusterCount,,total_children_count._sum,total_children_ClusterCount,,total_young_count._sum,total_young_ClusterCount,,V001,clusterid,,V024,region_v024,,V000,ctry_phase,,fever_full_treat_young_count._sum,fever_full_treat_ClusterCount,
    -> Results_by_cluster
    -> VariableRetriever
Results_by_cluster: Inspector [off]
VariableRetriever
    SCOPE = Global
    VALUE_ATTR = filecode
    VARNAME = currentFileCode
    -> AttributeCreator_3
Note: Set output names for dynamic writers
AttributeCreator_3
    ATTR_LIST = outTableName,@Value(filecode)_Fever_By_Cluster_Table_Weighted,outFCClusterName,S_@Value(filecode)_Fever_By_Cluster_Weighted
    -> StringReplacer
StringReplacer
    SRC_ATTRS = outFCClusterName,outTableName
    REGEXP = no
    REPLACE_TEXT = _
    CASE = no
    FIND_TEXT = .
    NO_MATCH = _FME_NO_OP_
    -> FeatureMerger_2 [input 2]
    -> File1 (writer CSV_6)
Note: Write CSV output results (always)
File1 (writer CSV_6)
    attributes: filecode text, region_v024 text, clusterid int, total_children_ClusterCount float, total_young_ClusterCount float, fever_occurrence_ClusterCount float, fever_full_treat_ClusterCount float, fever_any_treat_ClusterCount float, fever_occurrence_ClusterProp float, fever_full_treat_ClusterProp float, young_full_treat_ClusterProp float, fever_any_treat_ClusterProp float, young_any_treat_ClusterProp float
Note: NB / It is the responsibility of the user or caller to ensure the correct shapefile feature type name is provided. / The match is only done on cluster id which isn't unique between different surveys! A dummy value such as N/A must be provided if / no point shapefile is available otherwise it will read all!
FeatureMerger_2
    ATTR_ACCUM_MODE = Merge Supplier
    MERGE_TYPE = Attributes Only
    IGNORE_NULLS = No
    ATTR_CONFLICT_RES = Use Requestor
    JOIN_KEYS = @Value(DHSCLUST) @Value(clusterid) AUTO
    SUPPLIERS_FIRST = No
    PROCESS_DUPS = No
    MERGED -> Results_Geographic
    MERGED -> FeatureClass1 (writer FILEGDB_1)
    MERGED -> FeatureClass1 (writer GEODATABASE_FILE_2)
Note: Write point featureclass results if any
Results_Geographic: Inspector [off]
AttributeExposer
    ATTR_LIST = fme_basename

Bookmark: Accumulate and summarise by region (polygon)
Note: summarise by region V024, also grouping by country V000 so that these carry thru
StatisticsCalculator_2
    STATS_ATTRS = fever_any_treat_young_count fever_full_treat_young_count fever_young_count total_children_count total_young_count
    COMPUTE_HISTOGRAM = NO
    SUM_ATTR = _sum
    PREPEND_ATTR_NAME_CHOICE = For multiple results only
    GROUP_BY = V000 V024
    SUMMARY -> AttributeCreator_6
Note: Calculate proportion results from sums
AttributeCreator_6
    ATTR_LIST = fever_occurrence_RegionProp,@Evaluate(@Value(fever_young_count._sum)/@Value(total_young_count._sum)),young_any_treat_RegionProp,@Evaluate(@Value(fever_any_treat_young_count._sum)/@Value(total_young_count._sum)),young_full_treat_RegionProp,@Evaluate(@Value(fever_full_treat_young_count._sum)/@Value(total_young_count._sum)),fever_any_treat_RegionProp,@Evaluate(@Value(fever_any_treat_young_count._sum)/@Value(fever_young_count._sum)),fever_full_treat_RegionProp,@Evaluate(@Value(fever_full_treat_young_count._sum)/@Value(fever_young_count._sum))
    -> AttributeRenamer_2
AttributeRenamer_2
    ATTR_LIST = fever_any_treat_young_count._sum,fever_any_treat_RegionCount,,fever_young_count._sum,fever_occurrence_RegionCount,,total_children_count._sum,total_children_RegionCount,,total_young_count._sum,total_young_RegionCount,,V024,region_v024,,V000,ctry_phase,,fever_full_treat_young_count._sum,fever_full_treat_RegionCount,
    -> VariableRetriever_2
VariableRetriever_2
    SCOPE = Global
    VALUE_ATTR = filecode
    VARNAME = currentFileCode
    -> AttributeCreator_7
Note: Set output name for dynamic writer
AttributeCreator_7
    ATTR_LIST = outFCRegionName,S_@Value(filecode)_Fever_By_Region_Weighted,outTableName,@Value(filecode)_Fever_By_Region_Table_Weighted
    -> StringReplacer_2
StringReplacer_2
    SRC_ATTRS = outTableName,outFCRegionName
    REGEXP = no
    REPLACE_TEXT = _
    CASE = no
    FIND_TEXT = .
    NO_MATCH = _FME_NO_OP_
    -> FeatureClass10000 (writer CSV_6)
    -> StringSearcher
StringSearcher
    MATCHED_PARTS_ATTR = _survey_id
    MATCHED_RESULT_ATTR = _matched_characters
    STRING_TO_SEARCH = @Value(filecode)
    REGEXP = ^(\d+)\.\w+
    CASE = no
    MATCHED -> ListIndexer
ListIndexer
    INDEX = 0
    LIST_ATTR = _survey_id{}
    -> FeatureReader_2
FeatureReader_2
    GEODATABASE_FILE_QUERY_FEATURE_TYPES_FOR_MERGE_FILTERS = Yes
    INTERACT = <No Spatial Filter>
    GEODATABASE_FILE_SEARCH_ORDER = SPATIAL_FIRST
    COMBINE_GEOM = Use Result
    GEODATABASE_FILE_SPLIT_MULTI_PART_ANNOS = no
    GEODATABASE_FILE_CHECK_SIMPLE_GEOM = no
    GEODATABASE_FILE_CLIP_TO_ENVELOPE = NO
    ATTR_CONFLICT_RES = Use Result
    FEATURETYPES_RADIO = FEATURETYPES
    GEODATABASE_FILE_TRANSLATE_SPATIAL_DATA_ONLY = no
    GEODATABASE_FILE_SEARCH_METHOD = GEODB_INTERSECTS
    DATASET = $(Source_GDB_Boundaries)
    GEODATABASE_FILE_RESOLVE_SUBTYPE_NAMES = yes
    GEODATABASE_FILE_MERGE_FEAT_LINKED_ANNOS = no
    GEODATABASE_FILE_USE_SEARCH_ENVELOPE = NO
    OUTPUT_FEATURES_DISPLAY = Based on Connections
    GEODATABASE_FILE_IGNORE_RELATIONSHIP_INFO = yes
    GEODATABASE_FILE_RESOLVE_DOMAINS = no
    GEODATABASE_FILE_IGNORE_NETWORK_INFO = yes
    GEODATABASE_FILE_ALIAS_MODE = NONE
    WHERE = SVYID=@Value(_survey_id) AND REGCODE=@Value(region_v024)
    GEODATABASE_FILE_SPLIT_COMPLEX_ANNOS = no
    FEATURETYPES = dhs_subnational_boundaries_all_surveys
    ATTRIBUTES = dhs_subnational_boundaries_all_surveys,"OBJECTID,ISO,FIPS,DHSCC,SVYTYPE,SVYYEAR,CNTRYNAMEE,CNTRYNAMEF,CNTRYNAMES,DHSREGEN,DHSREGFR,DHSREGSP,SVYID,REG_ID,Svy_Map,MULTLEVEL,LEVELRNK,REGVAR,REGCODE,REGNAME,OTHREGVAR,OTHREGCO,OTHREGNA,LEVELCO,LEVELNA,REPALLIND,REGNOTES,SVYNOTES,Shape_Length,Shape_Area"
    ATTR_ACCUM_MODE = Merge Initiator and Result
    FORMAT = GEODATABASE_FILE
    GEODATABASE_FILE_SPLIT_COMPLEX_EDGES = no
    GEODATABASE_FILE_FEATURE_READ_MODE = Features
    GEODATABASE_FILE_CACHE_MULTIPATCH_TEXTURES = yes
    dhs_subnational_boundaries_all_surveys -> FeatureClass100 (writer GEODATABASE_FILE_2)
    <SCHEMA> -> FeatureClass100 (writer GEODATABASE_FILE_2)
    <SCHEMA> -> polygons_fileapi (writer FILEGDB_1)
    dhs_subnational_boundaries_all_surveys -> polygons_fileapi (writer FILEGDB_1)
Note: Write polygon featureclass results if any
FeatureClass100 (writer GEODATABASE_FILE_2)
    attributes: filecode char(12), total_children_RegionCount double, total_young_RegionCount double, fever_occurrence_RegionCount double, fever_full_treat_RegionCount double, fever_any_treat_RegionCount double, fever_occurrence_RegionProp double, fever_full_treat_RegionProp double, young_full_treat_RegionProp double, fever_any_treat_RegionProp double, young_any_treat_RegionProp double
polygons_fileapi (writer FILEGDB_1)
    attributes: filecode text(200), total_children_RegionCount double, total_young_RegionCount double, fever_occurrence_RegionCount double, fever_full_treat_RegionCount double, fever_any_treat_RegionCount double, fever_occurrence_RegionProp double, fever_full_treat_RegionProp double, young_full_treat_RegionProp double, fever_any_treat_RegionProp double, young_any_treat_RegionProp double
Note: Write CSV output results (always)
FeatureClass10000 (writer CSV_6)
    attributes: filecode text, region_v024 text, total_children_RegionCount float, total_young_RegionCount float, fever_occurrence_RegionCount float, fever_full_treat_RegionCount float, fever_any_treat_RegionCount float, fever_occurrence_RegionProp float, fever_full_treat_RegionProp float, young_full_treat_RegionProp float, fever_any_treat_RegionProp float, young_any_treat_RegionProp float
dhs_subnational_boundaries_all_surveys (reader GEODATABASE_FILE_1)
    attributes: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

Bookmark: View or save individual results
AttributeCreator [off]
    ATTR_LIST = poorly_prop_by_woman,@Evaluate(@Value(fever_young_count)/@Value(total_young_count))
    -> ResultsByIndividual [off]
ResultsByIndividual: Inspector [off]

Bookmark: Individual summary check
Note: If total young count > 6 then health record doesn't / cover all children (there are a max of 6 health records)
Tester_3
    BOOL_OP = OR
    TEST_MODE = Automatic
    TEST_CLAUSE = TEST @Value(total_young_count) > 6
    TEST_DESCRIPTION = ""
    PASSED -> WarningNotAllHealthRecordsPresent
WarningNotAllHealthRecordsPresent: Inspector

FME custom transformer FileExistenceChecker
This transformer checks if input file paths or directories exist and routes features accordingly.
You can set the "Input File Path" parameter to an attribute or a string.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- Input =   # Input File Path

Input (input)
    -> AttributeCreator
Note: Get parameter value
AttributeCreator
    NUM_PRIOR_FEATURES = 0
    NUM_SUBSEQUENT_FEATURES = 0
    ATTR_LIST = FEC_FullPath,$(Input)
    -> PythonCaller
Note: Use OS and zipfile libraries to / check if file exists
PythonCaller
    NEW_ATTRIBUTES = FEC_exists
    PYTHONSOURCE:
      import fmeobjects
      import os
      import zipfile

      def processFeature(feature):

         # Get input path attribute
         fullpath=feature.getAttribute("FEC_FullPath")

         # Check if the file exists
         if os.path.exists(fullpath):
            feature.setAttribute("FEC_exists","Yes")
         # if not, try checking inside a zip file
         else:
            fullpath = fullpath.replace("\\","/")
            idx = fullpath.find(".zip")
            if idx > -1:
                zipPath = fullpath[:idx+4]
                pathInZip = fullpath[idx+5:]    #i.e. .zip/
                try:
                    with zipfile.ZipFile(zipPath, 'r') as f:
                        if isinstance(f.getinfo(pathInZip),zipfile.ZipInfo):
                            feature.setAttribute("FEC_exists","Yes")
                            return
                except KeyError:
                    pass
            # not found in a zipfile or in filesystem - does not exist
            feature.setAttribute("FEC_exists","No")
    PYTHONSYMBOL = processFeature
    -> Tester
Note: PASSED=File exists
Tester
    BOOL_OP = OR
    TEST_MODE = Automatic
    TEST_CLAUSE = TEST @Value(FEC_exists) = Yes
    TEST_DESCRIPTION = ""
    PASSED -> AttributeRemover
    FAILED -> AttributeRemover_2
Exists (output)
Does_Not_Exist (output)

Bookmark: Cleanup
AttributeRemover
    REMOVE_ATTRS = FEC_FullPath,FEC_exists
    -> Exists (output)
AttributeRemover_2
    REMOVE_ATTRS = FEC_FullPath,FEC_exists
    -> Does_Not_Exist (output)
