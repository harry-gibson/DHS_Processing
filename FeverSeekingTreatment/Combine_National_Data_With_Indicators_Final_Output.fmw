FME workspace Combine_National_Data_With_Indicators_Final_Output.fmw

Parameters:
- SourceDataset_CSV = \\129.67.26.176\map_data\DHS_Automation\Processing\FeverSeekingTreatment_201507\Indicators\SurveyIndicatorsAnyYr.csv   # Source CSV (CommaSeparatedValue) File(s)
- SourceDataset_CSV_5 = \\129.67.26.176\map_data\DHS_Automation\Processing\FeverSeekingTreatment_201507\Results\Weighting\National\NationalSurveyResults_Weighted.csv   # Source CSV (CommaSeparatedValue) File(s)
- DestDataset_CSV = \\129.67.26.176\map_data\DHS_Automation\Processing\FeverSeekingTreatment_201507\Results\Weighting\National   # Destination CSV (CommaSeparatedValue) Folder

Readers:
- CSV_1: CSV from $(SourceDataset_CSV)
- CSV_2: CSV from $(SourceDataset_CSV_5)

Writers:
- CSV_3: CSV to $(DestDataset_CSV)

SurveyIndicatorsAnyYr (reader CSV_1)
    attributes: Country char(33), Survey_ID_num number(4,0), yrTo number(5,0), Electricity number(10,5), Electricity_IndicatorYearUsed number(5,0), GDP number(31,15), GDP_IndicatorYearUsed number(5,0), GDPGrowth number(12,9), GDPGrowth_IndicatorYearUsed number(5,0), GDPpercap number(13,7), GDPpercap_IndicatorYearUsed number(5,0), GNIpercap number(6,0), GNIpercap_IndicatorYearUsed number(5,0), HealthExpercap number(13,9), HealthExpercap_IndicatorYearUsed number(5,0), HealthExPub number(12,9), HealthExPub_IndicatorYearUsed number(5,0), HealthExTotal number(12,9), HealthExTotal_IndicatorYearUsed number(5,0), Literacy number(12,8), Literacy_IndicatorYearUsed number(5,0), PregWomenCare number(5,1), PregWomenCare_IndicatorYearUsed number(5,0), PrimaryComplete number(12,8), PrimaryComplete_IndicatorYearUsed number(5,0), RuralPop number(6,3), RuralPop_IndicatorYearUsed number(5,0), UrbanPop number(6,3), UrbanPop_IndicatorYearUsed number(5,0), CommHlthWrkrs number(5,3),
      CommHlthWrkrs_IndicatorYearUsed number(5,0), DPT number(3,0), DPT_IndicatorYearUsed number(5,0), NurseMidwives number(6,3), NurseMidwives_IndicatorYearUsed number(5,0), Country_DHSCode char(3), Country_ISO3Code char(4)
    -> FeatureMerger [input 2]
NationalSurveyResults_Weighted (reader CSV_2)
    attributes: filecode char(11), fever_any_treat_RegionCount._sum number(17,12), fever_full_treat_RegionCount._sum number(17,12), fever_occurrence_RegionCount._sum number(18,12), total_children_RegionCount._sum number(18,11), total_young_RegionCount._sum number(17,11), fever_full_treat_TotalProp number(19,16), fever_any_treat_TotalProp number(18,15), fever_occurrence_TotalProp number(18,16)
    -> StringSearcher
StringSearcher
    STRING_TO_SEARCH = @Value(filecode)
    MATCHED_RESULT_ATTR = _svyID
    CASE = no
    REGEXP = ^(\d+)
    MATCHED_PARTS_ATTR = _matched_parts
    MATCHED -> FeatureMerger [input 1]
FeatureMerger
    ATTR_ACCUM_MODE = Merge Supplier
    MERGE_TYPE = Attributes Only
    ATTR_CONFLICT_RES = Use Requestor
    PROCESS_DUPS = No
    JOIN_KEYS = @Value(_svyID) @Value(Survey_ID_num) AUTO
    SUPPLIERS_FIRST = No
    IGNORE_NULLS = No
    MERGED -> FeatureMerger_Merged
    MERGED -> national_fever_with_indicators_updated (writer CSV_3)
national_fever_with_indicators_updated (writer CSV_3)
    attributes: Country auto, Survey_ID_num auto, Country_DHSCode char(3), Country_ISO3Code char(4), yrTo auto, filecode char(11), fever_any_treat_RegionCount._sum auto, fever_full_treat_RegionCount._sum auto, fever_occurrence_RegionCount._sum auto, total_children_RegionCount._sum auto, total_young_RegionCount._sum auto, fever_full_treat_TotalProp auto, fever_any_treat_TotalProp auto, fever_occurrence_TotalProp auto, Electricity auto, Electricity_IndicatorYearUsed auto, GDP auto, GDP_IndicatorYearUsed auto, GDPGrowth auto, GDPGrowth_IndicatorYearUsed auto, GDPpercap auto, GDPpercap_IndicatorYearUsed auto, GNIpercap auto, GNIpercap_IndicatorYearUsed auto, HealthExpercap auto, HealthExpercap_IndicatorYearUsed auto, HealthExPub auto, HealthExPub_IndicatorYearUsed auto, HealthExTotal auto, HealthExTotal_IndicatorYearUsed auto,
      Literacy auto, Literacy_IndicatorYearUsed auto, PregWomenCare auto, PregWomenCare_IndicatorYearUsed auto, PrimaryComplete auto, PrimaryComplete_IndicatorYearUsed auto, RuralPop auto, RuralPop_IndicatorYearUsed auto, UrbanPop auto, UrbanPop_IndicatorYearUsed auto, CommHlthWrkrs auto, CommHlthWrkrs_IndicatorYearUsed auto, DPT auto, DPT_IndicatorYearUsed auto, NurseMidwives auto, NurseMidwives_IndicatorYearUsed auto
FeatureMerger_Merged: Inspector
