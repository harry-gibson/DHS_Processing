FME workspace summarise_fever_full_weighted_runner.fmw

Parameters:
- DestDataset_FILEGDB = C:\Temp\DHS_Weighting\Results_2\All_Weighted.gdb   # Destination Geodatabase
- InputFileDir = \\129.67.26.176\map_data\DHS_Automation\DataExtraction\20150626_FullSiteScrape\ProcessedTables   # directory containing input extracted records
- SurveySpecDir = \\129.67.26.176\map_data\DHS_Automation\DataExtraction\20150626_FullSiteScrape\ParsedSpecs   # Directory containing survey specification files
- OutCSVDir = C:\Temp\DHS_Weighting\Results_2   # Destination CSV Folder
- SurveyDataDir = \\129.67.26.176\map_data\DHS_Automation\Acquisition\20150626_FullSiteScrape\downloads   # Directory containing extracted surveys (in subdirs)
- H32_UseFields_CSV = \\129.67.26.176\map_data\DHS_Automation\Processing\FeverSeekingTreatment_201507\Info\MergedH32_AllEndemic_KB.csv   # CSV specifying which H32 fields should be used
- AvailableFeverDataCSV = \\129.67.26.176\map_data\DHS_Automation\Processing\FeverSeekingTreatment_201507\Info\AvailableFeverDataSummary.csv   # CSV file containing listing of fever vs ARI data availability

Readers:
- PATH_1: PATH from $(InputFileDir)
- CSV_1: CSV from $(H32_UseFields_CSV)
- CSV_2: CSV from $(AvailableFeverDataCSV)

Note: Read the names of all the .DAT files
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher
Note: Fidn the name of a shapefile in the survey's directory
StringSearcher
    MATCHED_RESULT_ATTR = _survey_idnum
    CASE = no
    REGEXP = ^\d+
    STRING_TO_SEARCH = @Value(path_filename)
    MATCHED_PARTS_ATTR = _matched_parts
    MATCHED -> StringCaseChanger
    MATCHED -> AttributeCreator_4
StringCaseChanger
    CHANGE_TYPE = UPPERCASE
    ATTRLIST = path_rootname
    ATTRCHOICE = Selected Attributes
    -> StringSearcher_2
StringSearcher_2
    MATCHED_RESULT_ATTR = _surveycode
    CASE = no
    REGEXP = ^\d+\.\w+
    STRING_TO_SEARCH = @Value(path_filename)
    MATCHED_PARTS_ATTR = _matched_parts
    MATCHED -> Survey_filecodes
    MATCHED -> FeatureMerger_3 [input 1]
Survey_filecodes: Inspector
AttributeCreator_4
    ATTR_LIST = _survey_subdirectory,$(SurveyDataDir)\@Value(_survey_idnum)
    -> AttributeKeeper_4
AttributeKeeper_4
    KEEP_ATTRS = _survey_idnum,_survey_subdirectory
    -> FeatureReader
FeatureReader
    DATASET = @Value(_survey_subdirectory)
    OUTPUT_FEATURES_DISPLAY = Based on Connections
    FORMAT = PATH
    ATTR_ACCUM_MODE = Merge Initiator and Result
    PATH_TYPE = FILE
    FEATURETYPES_RADIO = FEATURETYPES
    COMBINE_GEOM = Use Result
    ATTRS_TO_EXPOSE = path_windows
    PATH_GLOB_PATTERN = *.shp
    PATH_RETRIEVE_FILE_PROPERTIES = NO
    ATTR_CONFLICT_RES = Use Result
    <REJECTED> -> FeatureReader__Rejected_
    <OTHER> -> AttributeRenamer_2
AttributeRenamer_2
    ATTR_LIST = path_windows,survey_shapefile,
    -> Shapefiles_Found
    -> FeatureMerger [input 2]
Shapefiles_Found: Inspector
FeatureReader__Rejected_: Inspector
CSV (reader CSV_2)
    attributes: FileCode char(11), HasFeverData number(2,0), HasARIData number(2,0), H22_Label char(33), H31_Label char(33), H31B_Label char(31), H31C_Label char(53)
    -> AttributeKeeper_3
AttributeKeeper_3
    KEEP_ATTRS = FileCode,HasARIData,HasFeverData
    -> FeatureMerger_2 [input 2]
Note: Filter to surveys we want to run
FeatureMerger_3
    PROCESS_DUPS = No
    SUPPLIERS_FIRST = No
    ATTR_ACCUM_MODE = Merge Supplier
    IGNORE_NULLS = No
    MERGE_TYPE = Attributes Only
    ATTR_CONFLICT_RES = Use Requestor
    JOIN_KEYS = @Value(_surveycode) @Value(FileCode) AUTO
    MERGED -> SubstringExtractor_2
SubstringExtractor_2
    START = 0
    SRC_ATTR = path_rootname
    END = 1
    RESULT_ATTR = _surveyCtryCode
    -> SubstringExtractor_5
SubstringExtractor_5
    START = 4
    SRC_ATTR = path_rootname
    END = 5
    RESULT_ATTR = _surveySurveyCode
    -> SubstringExtractor_7
SubstringExtractor_7
    START = 4
    SRC_ATTR = path_rootname
    END = 4
    RESULT_ATTR = _surveyPhaseCode
    -> SubstringExtractor_9
SubstringExtractor_9
    START = 5
    SRC_ATTR = path_rootname
    END = 5
    RESULT_ATTR = _surveyVersionCode
    -> AttributeCreator
Note: Generate parameters specofying survey files to process
AttributeCreator
    ATTR_LIST = _rec01Path,$(InputFileDir)\@Value(_surveycode).REC01.CSV,_rec21Path,$(InputFileDir)\@Value(_surveycode).REC21.CSV,_rec43Path,$(InputFileDir)\@Value(_surveycode).REC43.CSV,_surveySpecPath,$(SurveySpecDir)\@Value(_surveycode).FlatRecordSpec.csv
    -> AttributeKeeper_2
AttributeKeeper_2
    KEEP_ATTRS = _rec01Path,_rec21Path,_rec43Path,_shapefileWildcardPath,_surveycode,_surveyCtryCode,_surveyPhaseCode,_surveySpecPath,_surveySurveyCode,_surveyVersionCode,path_rootname,_survey_idnum
    -> FeatureMerger_2 [input 1]
Note: Find out whether this survey has fever data
FeatureMerger_2
    PROCESS_DUPS = No
    SUPPLIERS_FIRST = No
    ATTR_ACCUM_MODE = Merge Supplier
    IGNORE_NULLS = No
    MERGE_TYPE = Attributes Only
    ATTR_CONFLICT_RES = Use Requestor
    JOIN_KEYS = @Value(_surveycode) @Value(FileCode) AUTO
    MERGED -> AttributeValueMapper
Note: Use ARI if no fever
AttributeValueMapper
    LUT = 0,1,1,0
    SRC = HasFeverData
    DIRECTION = Forward (Source To Destination)
    VAL_ATTR = _UseARI
    -> Tester
Tester
    TEST_DESCRIPTION = ""
    BOOL_OP = OR
    TEST_MODE = Automatic
    TEST_CLAUSE = TEST @Value(_UseARI) = 1
    PASSED -> FeatureMerger [input 1]
    PASSED -> ARI_ones_to_run
    FAILED -> FeatureMerger [input 1]
Note: See if there is a shapefile with identical name to the survey file
FeatureMerger
    PROCESS_DUPS = No
    SUPPLIERS_FIRST = No
    ATTR_ACCUM_MODE = Merge Supplier
    IGNORE_NULLS = No
    MERGE_TYPE = Attributes Only
    ATTR_CONFLICT_RES = Use Requestor
    JOIN_KEYS = @Value(_survey_idnum) @Value(_survey_idnum) AUTO
    MERGED -> WorkspaceRunner
    NOT_MERGED -> AttributeCreator_5
AttributeCreator_5
    ATTR_LIST = survey_shapefile,N/A
    -> WorkspaceRunner
Note: Run the workbench!
WorkspaceRunner
    BLOCKING = Yes
    WORKSPACE_FILE = $(FME_MF_DIR)summarise_fever_by_indiv_and_cluster_all_treatments_weighted.fmw
    WORKSPACE_PARAMETERS = REC21_CSV,@Value(_rec21Path),REC43_CSV,@Value(_rec43Path),REC01_CSV,@Value(_rec01Path),MaxAge,5,SurveyRecordSpec,@Value(_surveySpecPath),H32_UseFields_CSV,$(H32_UseFields_CSV),DestDataset_FILEGDB,$(DestDataset_FILEGDB),AllPointShapes,@Value(survey_shapefile),OutCSVDir,$(OutCSVDir),Source_GDB_Boundaries,\\129.67.26.176\map_data\DHS_Automation\SupportingInfo\DHS_Boundary_Data\full_download\sdr_subnational_boundaries_all_surveys.gdb,Use_ARI,@Value(_UseARI),DestDataset_GEODATABASE_FILE,$(DestDataset_FILEGDB)
    SUCCEEDED -> WorkspaceRunner_Succeeded
    FAILED -> WorkspaceRunner_Failed
    SUMMARY -> WorkspaceRunner_Summary
    FAILED -> Terminator
WorkspaceRunner_Succeeded: Inspector
WorkspaceRunner_Failed: Inspector
WorkspaceRunner_Summary: Inspector
Terminator [off]
    MESSAGE = Translation Terminated
ARI_ones_to_run: Inspector

Bookmark: Get the IDs of surveys that Kate has specified H32 usage for
CSV (reader CSV_1)
    attributes: FileCode char(11), RecordName char(6), RecordTypeValue char(4), Name char(5), Label char(74), Start number(4,0), Len number(2,0), Occurrences char(1), FMETYPE char(12), CountAsTreatmentGuess char(4), Note char(1), AnyTreatmentGuess char(4), Any_Treat char(2), OUTPUT_CountAsTreatmentSought char(2)
    -> AttributeKeeper_5
AttributeKeeper_5
    KEEP_ATTRS = FileCode
    -> DuplicateRemover
DuplicateRemover
    KEYATTR = FileCode
    UNIQUE -> FeatureMerger_3 [input 2]
