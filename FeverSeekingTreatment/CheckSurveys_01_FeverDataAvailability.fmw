FME workspace CheckSurveys_01_FeverDataAvailability.fmw

Parameters:
- SourceDataset_CSV_3 = C:\Users\zool1301\Documents\DHS\Scrape\ParsedSpecs\*FlatRecordSpec.csv   # Source CSV (CommaSeparatedValue) File(s)
- ProcessedTablePath = C:\Users\zool1301\Documents\DHS\Scrape\ProcessedTables   # Directory containing processed tables
- DestDataset_CSV = C:\Users\zool1301\Documents\DHS\Scrape\Info   # Destination CSV (CommaSeparatedValue) Folder

Readers:
- CSV_1: CSV from $(SourceDataset_CSV_3)

Writers:
- CSV_2: CSV to $(DestDataset_CSV)

Note: Read the survey specifications
CSV (reader CSV_1)
    attributes: FileCode text, RecordName text, RecordTypeValue text, RecordLabel text, Name text, Label text, Start text, Len text, Occurrences text, ZeroFill text, DecimalChar text, Decimal text, FMETYPE text
    -> TestFilter
    -> AttributeKeeper_2
AttributeKeeper_2
    KEEP_ATTRS = FileCode
    -> Sampler_3
Sampler_3
    GROUP_BY = FileCode
    RATE = 1
    SAMPLE_TYPE_LONG = First N Features
    SAMPLED -> AttributeCreator
AttributeCreator
    ATTR_LIST = Rec43_Path,$(ProcessedTablePath)\@Value(FileCode).REC43.CSV,HasFeverData,0,HasARIData,0,HasHealthRecordTable,0
    -> FileExistenceChecker
Note: Does this survey even have a REC43 (child's health) table?
Note: This workbench scans a directory of processed DHS survey specification files (which is created previously by a python script) and also the REC43 data tables of those surveys to identify: / - whether the table containing fever data (REC43) even exists / - What the text content of the fever-related questions asks for that survey / - Whether the fever-related questions are actually populated for that survey (i.e. there is at least one yes answer somewhere) / The output is an AvailableDataSummary file which can then be checked to make sure the questions all ask something useful (and didn't mean something completely different in a particular survey).
FileExistenceChecker
    Input = @Value(Rec43_Path)
    Exists -> AttributeCreator_4
    Does_Not_Exist -> FeatureMerger [input 1]
AttributeCreator_4
    ATTR_LIST = HasHealthRecordTable,1
    -> FeatureReader
    -> FeatureMerger [input 1]
Note: Read the REC43 data
FeatureReader
    ATTR_ACCUM_MODE = Merge Initiator and Result
    OUTPUT_FEATURES_DISPLAY = Based on Connections
    ATTRS_TO_EXPOSE = H22 H31 H31B H31C
    FEATURETYPES_RADIO = FEATURETYPES
    CSV__IN_FIELD_NAMES = YES
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV_SCAN_MAX_FEATURES = 10000
    COMBINE_GEOM = Use Result
    CSV__SCHEMA = number,3,0,number,2,0,number,2,0,char,1,,char,1,,number,5,0,number,3,0,number,3,0,number,2,0,number,2,0,number,2,0,number,2,0,number,2,0,number,2,0,char,1,,char,1,,char,1,,number,2,0,number,2,0,number,2,0,number,2,0,number,2,0,number,2,0,char,1,,number,2,0,number,2,0,number,2,0,char,1,,number,2,0,number,2,0,char,1,,char,1,,char,1,,char,1,,char,1,,char,1,,char,1,,number,2,0,number,5,0,number,3,0,number,3,0,number,2,0,number,2,0,number,2,0,number,2,0,char,1,,char,1,,number,2,0,number,2,0,number,2,0,char,1,,char,1,,char,1,,number,2,0,number,2,0,number,2,0,number,2,0,number,2,0,number,2,0,char,1,,char,1,,char,1,,number,2,0,number,2,0,number,2,0,char,1,,number,2,0,number,2,0,number,2,0,number,2,0,number,2,0,number,2,0,number,2,0,number,2,0,number,2,0,number,2,0,number,2,0,char,1,,char,1,,char,1,,char,1,,number,2,0,number,2,0,number,2,0,number,2,0,number,2,0,number,2,0,number,2,0,number,2,0,number,2,0,number,2,0,number,2,0,char,1,,number,2,0,number,2,0,number,2,0,number,2,0,char,1,,char,1,,number,2,0,number,2,0,number,2,0,char,1,,char,1,,char,1,,number,2,0,number,2,0,number,2,0,number,2,0,number,2,0,number,2,0,char,1,,char,1,,char,1,,number,2,0,number,2,0,number,2,0,char,1,,number,2,0,number,2,0,number,2,0,number,2,0,number,2,0,number,5,0,number,3,0,number,3,0,number,2,0,number,5,0,number,3,0,number,3,0,number,2,0,number,5,0,number,3,0,number,3,0,number,2,0,number,5,0,number,3,0,number,3,0,number,2,0,number,5,0,number,3,0,number,3,0,number,2,0,number,5,0,number,3,0,number,3,0,number,2,0,number,5,0,number,3,0,number,3,0,number,2,0,number,5,0,number,3,0,number,3,0,number,2,0,number,5,0,number,3,0,number,3,0,number,2,0,number,2,0,number,2,0,char,8,,char,1,,number,2,0,char,1,,number,3,0,char,1,,char,1,
    DATASET = @Value(Rec43_Path)
    CSV__FIELD_NAMES_AFTER_HEADER = no
    ATTR_CONFLICT_RES = Use Result
    CSV__SKIP_LINES = 1
    CSV__SKIP_FOOTER = 0
    CSV__DUPLICATE_DELIMS = no
    CSV__STRIP_QUOTES = yes
    FORMAT = CSV
    CSV__IN_SEPARATOR = ,
    CSV__SCHEMA_WITH_COL_NAMES = H44A,number,3,0,H43,number,2,0,H42,number,2,0,H41B,char,1,,H41A,char,1,,H40Y,number,5,0,H40M,number,3,0,H40D,number,3,0,H40,number,2,0,H39,number,2,0,H38,number,2,0,H37Z,number,2,0,H37Y,number,2,0,H37X,number,2,0,H37P,char,1,,H37O,char,1,,H37N,char,1,,H37M,number,2,0,H37L,number,2,0,H37K,number,2,0,H37J,number,2,0,H37I,number,2,0,H37H,number,2,0,H37G,char,1,,H37F,number,2,0,H37E,number,2,0,H37D,number,2,0,H37C,char,1,,H37B,number,2,0,H37A,number,2,0,H36F,char,1,,H36E,char,1,,H36D,char,1,,H36C,char,1,,H36B,char,1,,H36A,char,1,,H35,char,1,,H34,number,2,0,H33Y,number,5,0,H33M,number,3,0,H33D,number,3,0,H33,number,2,0,H32Z,number,2,0,H32Y,number,2,0,H32X,number,2,0,H32W,char,1,,H32V,char,1,,H32U,number,2,0,H32T,number,2,0,H32S,number,2,0,H32R,char,1,,H32Q,char,1,,H32P,char,1,,H32O,number,2,0,H32N,number,2,0,H32M,number,2,0,H32L,number,2,0,H32K,number,2,0,H32J,number,2,0,H32I,char,1,,H32H,char,1,,H32G,char,1,,H32F,number,2,0,H32E,number,2,0,H32D,number,2,0,H32C,char,1,,H32B,number,2,0,H32A,number,2,0,H31E,number,2,0,H31D,number,2,0,H31C,number,2,0,H31B,number,2,0,H31,number,2,0,H22,number,2,0,H21,number,2,0,H21A,number,2,0,H20,number,2,0,H15M,char,1,,H15L,char,1,,H15K,char,1,,H15J,char,1,,H15I,number,2,0,H15H,number,2,0,H15G,number,2,0,H15F,number,2,0,H15E,number,2,0,H15D,number,2,0,H15C,number,2,0,H15B,number,2,0,H15A,number,2,0,H15,number,2,0,H14,number,2,0,H13B,char,1,,H13,number,2,0,H12Z,number,2,0,H12Y,number,2,0,H12X,number,2,0,H12W,char,1,,H12V,char,1,,H12U,number,2,0,H12T,number,2,0,H12S,number,2,0,H12R,char,1,,H12Q,char,1,,H12P,char,1,,H12O,number,2,0,H12N,number,2,0,H12M,number,2,0,H12L,number,2,0,H12K,number,2,0,H12J,number,2,0,H12I,char,1,,H12H,char,1,,H12G,char,1,,H12F,number,2,0,H12E,number,2,0,H12D,number,2,0,H12C,char,1,,H12B,number,2,0,H12A,number,2,0,H11B,number,2,0,H11,number,2,0,H10,number,2,0,H0Y,number,5,0,H0M,number,3,0,H0D,number,3,0,H0,number,2,0,H9Y,number,5,0,H9M,number,3,0,H9D,number,3,0,H9,number,2,0,H8Y,number,5,0,H8M,number,3,0,H8D,number,3,0,H8,number,2,0,H7Y,number,5,0,H7M,number,3,0,H7D,number,3,0,H7,number,2,0,H6Y,number,5,0,H6M,number,3,0,H6D,number,3,0,H6,number,2,0,H5Y,number,5,0,H5M,number,3,0,H5D,number,3,0,H5,number,2,0,H4Y,number,5,0,H4M,number,3,0,H4D,number,3,0,H4,number,2,0,H3Y,number,5,0,H3M,number,3,0,H3D,number,3,0,H3,number,2,0,H2Y,number,5,0,H2M,number,3,0,H2D,number,3,0,H2,number,2,0,H1,number,2,0,HIDX,number,2,0,CASEID,char,8,,H44C,char,1,,H47,number,2,0,H46B,char,1,,H46A,number,3,0,H45,char,1,,H44B,char,1,
    CSV__GROUP_BY_DATASET = no
    CSV__ALLOW_SPACES_IN_COLUMN_NAMES = yes
    <OTHER> -> Tester_3
    <OTHER> -> Tester_5
Note: Is H22 set (Fever)
Tester_3
    TEST_DESCRIPTION = ""
    TEST_MODE = Automatic
    BOOL_OP = OR
    TEST_CLAUSE = TEST @Value(H22) = 1
    PASSED -> Sampler_4
Note: Just keep a matching value for each survey
Sampler_4
    GROUP_BY = FileCode
    RATE = 1
    SAMPLE_TYPE_LONG = First N Features
    SAMPLED -> AttributeCreator_2
AttributeCreator_2
    ATTR_LIST = HasFeverData,1
    -> AttributeKeeper_3
AttributeKeeper_3
    KEEP_ATTRS = FileCode,HasFeverData
    -> FeatureMerger [input 2]
Note: Is H31 AND (H31B OR H31C) set? (ARI)
Tester_5
    TEST_DESCRIPTION = ""
    TEST_MODE = Automatic
    COMPOSITE_TEST = "1 AND (2 OR 3)"
    BOOL_OP = COMPOSITE
    TEST_CLAUSE:
      TEST @Value(H31) BETWEEN 1,7
      TEST @Value(H31B) BETWEEN 1,7
      TEST @Value(H31C) BETWEEN 1,7
    PASSED -> Sampler_5
Sampler_5
    GROUP_BY = FileCode
    RATE = 1
    SAMPLE_TYPE_LONG = First N Features
    SAMPLED -> AttributeCreator_3
AttributeCreator_3
    ATTR_LIST = HasARIData,1
    -> AttributeKeeper_4
AttributeKeeper_4
    KEEP_ATTRS = FileCode,HasARIData
    -> FeatureMerger [input 2]
TestFilter
    TEST_LIST = BOOL_OP,OR,COMPOSITE_TEST,<Unused>,TEST_CLAUSE,"TEST @Value(Name) = H22",@Value(Name) = H22,BOOL_OP,OR,COMPOSITE_TEST,<Unused>,TEST_CLAUSE,"TEST @Value(Name) = H31",@Value(Name) = H31,BOOL_OP,OR,COMPOSITE_TEST,<Unused>,TEST_CLAUSE,"TEST @Value(Name) = H31B",@Value(Name) = H31B,BOOL_OP,OR,COMPOSITE_TEST,<Unused>,TEST_CLAUSE,"TEST @Value(Name) = H31C",@Value(Name) = H31C
    DEFAULT_VALUE = <UNFILTERED>
    @Value(Name) = H22 -> AttributeRenamer
    @Value(Name) = H31 -> AttributeRenamer_2
    @Value(Name) = H31B -> AttributeRenamer_3
    @Value(Name) = H31C -> AttributeRenamer_4
Note: Get the names (labels) for the fever and ARI variables so we can check they mean what we think
AttributeRenamer
    ATTR_LIST = Label,H22_Label,
    -> AttributeKeeper
AttributeKeeper
    KEEP_ATTRS = FileCode,H22_Label,H31_Label,H31B_Label,H31C_Label
    -> FeatureMerger [input 2]
AttributeRenamer_2
    ATTR_LIST = Label,H31_Label,
    -> AttributeKeeper_5
AttributeKeeper_5
    KEEP_ATTRS = FileCode,H22_Label,H31_Label,H31B_Label,H31C_Label
    -> FeatureMerger [input 2]
AttributeRenamer_3
    ATTR_LIST = Label,H31B_Label,
    -> AttributeKeeper_6
AttributeKeeper_6
    KEEP_ATTRS = FileCode,H22_Label,H31_Label,H31B_Label,H31C_Label
    -> FeatureMerger [input 2]
AttributeRenamer_4
    ATTR_LIST = Label,H31C_Label,
    -> AttributeKeeper_7
AttributeKeeper_7
    KEEP_ATTRS = FileCode,H22_Label,H31_Label,H31B_Label,H31C_Label
    -> FeatureMerger [input 2]
FeatureMerger
    SUPPLIERS_FIRST = No
    GEOM_TYPE = Build Polygons
    IGNORE_NULLS = No
    ATTR_ACCUM_MODE = Merge Supplier
    JOIN_KEYS = @Value(FileCode) @Value(FileCode) AUTO
    ATTR_CONFLICT_RES = Use Supplier
    PROCESS_DUPS = Yes
    MERGE_TYPE = Attributes Only
    MERGED -> AvailableFeverDataSummary (writer CSV_2)
    NOT_MERGED -> FeatureMerger_NotMerged
    MERGED -> FeatureMerger_Merged
FeatureMerger_Merged: Inspector
AvailableFeverDataSummary (writer CSV_2)
    attributes: FileCode text, HasFeverData auto, HasARIData auto, H22_Label auto, H31_Label auto, H31B_Label auto, H31C_Label auto
FeatureMerger_NotMerged: Inspector

FME custom transformer FileExistenceChecker
This transformer checks if input file paths or directories exist and routes features accordingly.
You can set the "Input File Path" parameter to an attribute or a string.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- Input =   # Input File Path

Input (input)
    -> AttributeCreator
Note: Get parameter value
AttributeCreator
    ATTR_LIST = FEC_FullPath,$(Input)
    NUM_PRIOR_FEATURES = 0
    NUM_SUBSEQUENT_FEATURES = 0
    -> PythonCaller
Note: Use OS and zipfile libraries to / check if file exists
PythonCaller
    PYTHONSYMBOL = processFeature
    NEW_ATTRIBUTES = FEC_exists
    PYTHONSOURCE:
      import fmeobjects
      import os
      import zipfile

      def processFeature(feature):

         # Get input path attribute
         fullpath=feature.getAttribute("FEC_FullPath")

         # Check if the file exists
         if os.path.exists(fullpath):
            feature.setAttribute("FEC_exists","Yes")
         # if not, try checking inside a zip file
         else:
            fullpath = fullpath.replace("\\","/")
            idx = fullpath.find(".zip")
            if idx > -1:
                zipPath = fullpath[:idx+4]
                pathInZip = fullpath[idx+5:]    #i.e. .zip/
                try:
                    with zipfile.ZipFile(zipPath, 'r') as f:
                        if isinstance(f.getinfo(pathInZip),zipfile.ZipInfo):
                            feature.setAttribute("FEC_exists","Yes")
                            return
                except KeyError:
                    pass
            # not found in a zipfile or in filesystem - does not exist
            feature.setAttribute("FEC_exists","No")
    -> Tester
Note: PASSED=File exists
Tester
    TEST_DESCRIPTION = ""
    TEST_MODE = Automatic
    BOOL_OP = OR
    TEST_CLAUSE = TEST @Value(FEC_exists) = Yes
    PASSED -> AttributeRemover
    FAILED -> AttributeRemover_2
Exists (output)
Does_Not_Exist (output)

Bookmark: Cleanup
AttributeRemover
    REMOVE_ATTRS = FEC_FullPath,FEC_exists
    -> Exists (output)
AttributeRemover_2
    REMOVE_ATTRS = FEC_FullPath,FEC_exists
    -> Does_Not_Exist (output)
