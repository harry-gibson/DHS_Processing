FME workspace Attach_Worldbank_Indicators_NearestYear.fmw

Parameters:
- SourceDataset_CSV_3 = C:\Users\zool1301\Documents\DHS\DHS_Info\SurveyIDs_With_Country_Details.csv   # Source CSV (CommaSeparatedValue) File(s)
- SourceDataset_CSV = ""\\129.67.26.176\map_data\Malaria data\Treatment Seeking for fever\AllEndemicSurveys_June2015\National\WorldBankIndicators\CommHlthWrkrs.csv" "\\129.67.26.176\map_data\Malaria data\Treatment Seeking for fever\AllEndemicSurveys_June2015\National\WorldBankIndicators\DPT.csv" "\\129.67.26.176\map_data\Malaria data\Treatment Seeking for fever\AllEndemicSurveys_June2015\National\WorldBankIndicators\Electricity.csv" "\\129.67.26.176\map_data\Malaria data\Treatment Seeking for fever\AllEndemicSurveys_June2015\National\WorldBankIndicators\GDP.csv" "\\129.67.26.176\map_data\Malaria data\Treatment Seeking for fever\AllEndemicSurveys_June2015\National\WorldBankIndicators\GDPGrowth.csv" "\\129.67.26.176\map_data\Malaria data\Treatment Seeking for fever\AllEndemicSurveys_June2015\National\WorldBankIndicators\GDPpercap.csv" "\\129.67.26.176\map_data\Malaria data\Treatment Seeking for fever\AllEndemicSurveys_June2015\National\WorldBankIndicators\GNIpercap.csv" "\\129.67.26.176\map_data\Malaria data\Treatment Seeking for fever\AllEndemicSurveys_June2015\National\WorldBankIndicators\HealthExpercap.csv" "\\129.67.26.176\map_data\Malaria data\Treatment Seeking for fever\AllEndemicSurveys_June2015\National\WorldBankIndicators\HealthExPub.csv" "\\129.67.26.176\map_data\Malaria data\Treatment Seeking for fever\AllEndemicSurveys_June2015\National\WorldBankIndicators\HealthExTotal.csv" "\\129.67.26.176\map_data\Malaria data\Treatment Seeking for fever\AllEndemicSurveys_June2015\National\WorldBankIndicators\Literacy.csv" "\\129.67.26.176\map_data\Malaria data\Treatment Seeking for fever\AllEndemicSurveys_June2015\National\WorldBankIndicators\NurseMidwives.csv" "\\129.67.26.176\map_data\Malaria data\Treatment Seeking for fever\AllEndemicSurveys_June2015\National\WorldBankIndicators\PregWomenCare.csv" "\\129.67.26.176\map_data\Malaria data\Treatment Seeking for fever\AllEndemicSurveys_June2015\National\WorldBankIndicators\PrimaryComplete.csv" "\\129.67.26.176\map_data\Malaria data\Treatment Seeking for fever\AllEndemicSurveys_June2015\National\WorldBankIndicators\RuralPop.csv" "\\129.67.26.176\map_data\Malaria data\Treatment Seeking for fever\AllEndemicSurveys_June2015\National\WorldBankIndicators\UrbanPop.csv""   # Source CSV (CommaSeparatedValue) File(s)
- FEATURE_TYPES =
- DestDataset_CSV = C:\Temp\DHS_Weighting\Results\Indicators   # Destination CSV (CommaSeparatedValue) Folder

Readers:
- CSV_1: CSV from $(SourceDataset_CSV_3)
- CSV_2: CSV from $(SourceDataset_CSV)

Writers:
- CSV_3: CSV to $(DestDataset_CSV)

Note: This workbench reads in the national summary data produced from aggregating the regional results of the fever treatment extraction work. One row = one survey. / It then attaches to each row each worldbank indicator value for the corresponding year and country to the survey. / The catch is that there isn't necessarily a worldbank indicator valuie for the relevant country in the survey year, and indeed there isn't the same availability for each indicator in a given country / year. / So instead we identify for each survey (year) and each indicator, the nearest year to the survey year that there is a worldbank value for, and use that (and record which year we used for each indicator). This necessitates some juggling of the shape of the incoming data to use the attribute name (the year) as a value to compare with the survey year.
Note: Read in the survey identifiers; we use these to get the year of the survey (taken as the year to)
CSV (reader CSV_1)
    attributes: Country char(33), Year char(8), Survey_ID_num number(4,0), SurveyAPI_ID char(10), Type char(4), Dataset range min char(8), Dataset range max char(7), IgnoreDupe number(2,0), DHS char(3), ISO3 char(4), ISO2 char(3), GAUL number(6,0)
    -> StringSearcher
Note: Parse the year of the survey. This may be a single number like 2000 or a range like 2008-09. For the latter case split it up and build the end year
StringSearcher
    REGEXP = (\d+)-(\d+)
    STRING_TO_SEARCH = @Value(Year)
    MATCHED_RESULT_ATTR = _tmp
    MATCHED_PARTS_ATTR = _yrRaw
    CASE = no
    MATCHED -> ListIndexer
    NOT_MATCHED -> AttributeCopier
ListIndexer
    INDEX = 0
    LIST_ATTR = _yrRaw{}
    PREFIX = yrFrom
    -> ListIndexer_2
ListIndexer_2
    INDEX = 1
    LIST_ATTR = _yrRaw{}
    PREFIX = yrTo
    -> SubstringExtractor
SubstringExtractor
    SRC_STRING = @Value(yrFrom_yrRaw)
    START = 0
    END = 1
    RESULT_ATTR = _century
    -> AttributeCreator
AttributeCreator
    ATTR_LIST = yrTo_yrRaw,@Value(_century)@Value(yrTo_yrRaw)
    -> AttributeRenamer
AttributeRenamer
    ATTR_LIST = yrFrom_yrRaw,yrFrom,,yrTo_yrRaw,yrTo,
    -> Tester
Note: A string like 1999-02 will now have been parsed into 1999 - 1902, so if this has happened add 100 to the end year
Tester
    TEST_MODE = Automatic
    TEST_CLAUSE = TEST @Value(yrTo) < @Value(yrFrom)
    BOOL_OP = OR
    TEST_DESCRIPTION = ""
    PASSED -> AttributeCreator_2
    FAILED -> AttributeKeeper_2
AttributeCreator_2
    ATTR_LIST = yrTo,@Evaluate(@Value(yrTo)+100)
    -> AttributeKeeper_2
AttributeCopier
    ATTR_LIST = Year,yrTo,
    -> AttributeRenamer_2
AttributeRenamer_2
    ATTR_LIST = Year,yrFrom,
    -> AttributeKeeper_2
AttributeKeeper_2
    KEEP_ATTRS = Country,Survey_ID_num,yrFrom,yrTo,DHS,ISO3
    -> FeatureMerger [input 1]
    -> FeatureMerger_3 [input 1]
Note: Read the WB indicator files. / Note the stupid denormalised format where each year is in its own attribute. / Also note that the indicator name column is more of a fireside chat with units and stuff also in there. The filename itself is a better indicator name, so copy that into the indicator name attribute.
CSV (reader CSV_2)
    attributes: Country Name char(47), Country Code char(4), Indicator Name char(40), Indicator Code char(15), 1960 char(1), 1961 char(1), 1962 char(1), 1963 char(1), 1964 char(1), 1965 char(1), 1966 char(1), 1967 char(1), 1968 char(1), 1969 char(1), 1970 char(1), 1971 char(1), 1972 char(1), 1973 char(1), 1974 char(1), 1975 char(1), 1976 char(1), 1977 char(1), 1978 char(1), 1979 char(1), 1980 char(1), 1981 char(1), 1982 char(1), 1983 char(1), 1984 char(1), 1985 char(1),
      1986 char(1), 1987 char(1), 1988 char(1), 1989 char(1), 1990 number(13,8), 1991 char(1), 1992 char(1), 1993 char(1), 1994 char(1), 1995 char(1), 1996 char(1), 1997 char(1), 1998 char(1), 1999 char(1), 2000 number(13,8), 2001 char(1), 2002 char(1), 2003 char(1), 2004 char(1), 2005 char(1), 2006 char(1), 2007 char(1), 2008 char(1), 2009 char(1), 2010 number(13,8), 2011 char(1), 2012 char(1), 2013 char(1), 2014 char(1)
    -> AttributeExposer
AttributeExposer
    ATTR_LIST = fme_basename
    -> AttributeCopier_2
AttributeCopier_2
    ATTR_LIST = fme_basename,indicatorname,
    -> AttributeRemover
AttributeRemover
    REMOVE_ATTRS = Country Name,fme_basename,Indicator Code,Indicator Name
    -> AttributeExploder
Note: Split into one feature per attribute i.e. a single year per feature / (normalise)
AttributeExploder
    ATTR_NAME_LABEL = _attr_name
    KEEP_GEOMETRY = No
    KEEP_ATTRIBUTES = Yes
    ATTR_VALUE_LABEL = _attr_value
    EXPLODING_TYPE = Features
    -> AttributeKeeper
Note: We elected to keep the source attributes as well when exploding, but we should immediately to keep only those we need as there will be hundreds of thousands of features here
AttributeKeeper
    KEEP_ATTRS = _attr_name,_attr_value,indicatorname,Country Code
    -> Tester_3
Tester_3
    TEST_MODE = Automatic
    TEST_CLAUSE:
      TEST _attr_value NOT_ATTRIBUTE_IS_EMPTY ""
      TEST _attr_value NOT_ATTRIBUTE_VALUE_NULL ""
    BOOL_OP = AND
    TEST_DESCRIPTION = ""
    PASSED -> FeatureMerger [input 2]
Note: For each survey, join all indicator / year pairs for that country
FeatureMerger
    ATTR_CONFLICT_RES = Use Requestor
    IGNORE_NULLS = Yes
    LIST_NAME = _mergedIndicators
    MERGE_TYPE = Attributes Only
    GEOM_TYPE = Build Polygons
    SUPPLIERS_FIRST = No
    JOIN_KEYS = @Value(ISO3) @Value(Country Code) AUTO
    PROCESS_DUPS = Yes
    ATTR_ACCUM_MODE = Merge Supplier
    NOT_MERGED -> FeatureMerger_NotMerged
    MERGED -> AttributeRemover_2
AttributeRemover_2
    REMOVE_ATTRS = _attr_name,_attr_value,DHS,indicatorname
    -> ListExploder
ListExploder
    INDEX_ATTR = _element_index
    ATTR_ACCUM_MODE = Merge Incoming List
    LIST_ATTR = _mergedIndicators{}
    ATTR_CONFLICT_RES = Use Original
    LIST_FOUND -> AttributeCreator_3
Note: SNEAKY BIT HERE / Having exploded the list we now have one feature for each survey / indicator / available year combination. / Calculate for each of these how different the indicator year is from the survey year (if at all)
AttributeCreator_3
    ATTR_LIST = _indicatorOffset,"FME_CONDITIONAL:DEFAULT_VALUE'9999'BOOL_OP;OR;COMPOSITE_TEST;<Unused>;TEST @Value(_attr_name) MATCHES_REGEX ^\d+$'@Evaluate(@abs(@Value(yrTo)-@Value(_attr_name)))'FME_NUM_CONDITIONS2___"
    -> Tester_2
Tester_2
    TEST_MODE = Automatic
    TEST_CLAUSE = TEST @Value(_indicatorOffset) != 9999
    BOOL_OP = OR
    TEST_DESCRIPTION = ""
    PASSED -> Sorter
Note: For each survey and indicator, take the features representing the indicator year that is closest to the survey year, by sorting then taking the first (c.f. SELECT / GROUP BY / ORDER BY / LIMIT 1)
Sorter
    SORT_PARM = Survey_ID_num NUMERIC ASCENDING indicatorname ALPHA ASCENDING _indicatorOffset NUMERIC ASCENDING
    SORTED -> Sampler
Sampler
    GROUP_BY = indicatorname Survey_ID_num
    SAMPLE_TYPE_LONG = First N Features
    RATE = 1
    SAMPLED -> AttributeRenamer_3
AttributeRenamer_3
    ATTR_LIST = _attr_name,_IndicatorYearUsed,
    -> BulkAttributeRenamer
    -> Sampler_Sampled
Note: This use of the bulkattributerenamer is sneaky, it renames one attribute to a name that is given in the value of another attribute. / This means that the workspace doesn't know what the attribute name will be coming out, as this can't be known until runtime, so the writer attributes have to be defined manually.
BulkAttributeRenamer
    REPLACE_STR = @Value(indicatorname)
    ATTRLIST = _attr_value
    PATTERN_ACTION_DISP = Regular Expression Replace
    REPLACE_PATTERN = .*
    ATTRCHOICE = Selected Attributes
    -> BulkAttributeRenamer_2
BulkAttributeRenamer_2
    REPLACE_STR = @Value(indicatorname)
    ATTRLIST = _IndicatorYearUsed
    PATTERN_ACTION_DISP = Add String Prefix
    ATTRCHOICE = Selected Attributes
    -> AttributeRemover_3
AttributeRemover_3
    REMOVE_ATTRS = _attr_value,_dhsCC,_element_index,Country,DHS,indicatorname,yrFrom,yrTo
    -> BulkAttributeRenamer_Output
    -> FeatureMerger_3 [input 2]
Note: Allow Process Duplicate Suppliers so that the incoming name / value pair attributes all accumulate onto the source survey row feature - there will be one for each indicator
FeatureMerger_3
    ATTR_CONFLICT_RES = Use Requestor
    IGNORE_NULLS = No
    MERGE_TYPE = Attributes Only
    GEOM_TYPE = Build Polygons
    SUPPLIERS_FIRST = No
    JOIN_KEYS = @Value(Survey_ID_num) @Value(Survey_ID_num) AUTO
    PROCESS_DUPS = Yes
    ATTR_ACCUM_MODE = Merge Supplier
    MERGED -> FeatureMerger_3_Merged
    MERGED -> SurveyIndicatorsAnyYr (writer CSV_3)
Note: Note the red / unconnected attributes on this. These will be filled at runtime thanks to the bulk attribute renamer, but it's reliant on the names being manually set correctly to match the indicator filenames.
SurveyIndicatorsAnyYr (writer CSV_3)
    attributes: Country char(33), Survey_ID_num number(4,0), yrTo auto, Country_DHSCode auto, Country_ISO3Code auto, Electricity auto, Electricity_IndicatorYearUsed auto, GDP auto, GDP_IndicatorYearUsed auto, GDPGrowth auto, GDPGrowth_IndicatorYearUsed auto, GDPpercap auto, GDPpercap_IndicatorYearUsed auto, GNIpercap auto, GNIpercap_IndicatorYearUsed auto, HealthExpercap auto, HealthExpercap_IndicatorYearUsed auto, HealthExPub auto, HealthExPub_IndicatorYearUsed auto, HealthExTotal auto, HealthExTotal_IndicatorYearUsed auto, Literacy auto, Literacy_IndicatorYearUsed auto, PregWomenCare auto, PregWomenCare_IndicatorYearUsed auto, PrimaryComplete auto, PrimaryComplete_IndicatorYearUsed auto, RuralPop auto, RuralPop_IndicatorYearUsed auto, UrbanPop auto,
      UrbanPop_IndicatorYearUsed auto, CommHlthWrkrs auto, CommHlthWrkrs_IndicatorYearUsed auto, DPT auto, DPT_IndicatorYearUsed auto, NurseMidwives auto, NurseMidwives_IndicatorYearUsed auto
FeatureMerger_3_Merged: Inspector
BulkAttributeRenamer_Output: Inspector
Sampler_Sampled: Inspector
FeatureMerger_NotMerged: Inspector
