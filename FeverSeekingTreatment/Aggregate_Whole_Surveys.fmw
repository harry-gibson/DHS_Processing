FME workspace Aggregate_Whole_Surveys.fmw

Parameters:
- SourceDataset_CSV_3 = \\129.67.26.176\map_data\DHS_Automation\Processing\FeverSeekingTreatment_201507\Results\Weighting\*_Fever_By_Region_Table_Weighted.csv   # Source CSV (CommaSeparatedValue) File(s)
- DestDataset_CSV = \\129.67.26.176\map_data\DHS_Automation\Processing\FeverSeekingTreatment_201507\Results\Weighting\National   # Destination CSV (CommaSeparatedValue) Folder

Readers:
- CSV_1: CSV from $(SourceDataset_CSV_3)

Writers:
- CSV_2: CSV to $(DestDataset_CSV)

Note: This workbench isn't very complicated. It aggregates the regional data from all the surveys into a single national feature for each survey (for subsequent comparison against the world bank indicators data). / Obviously, it just sums the count columns and then recalculates the proportion ones that are derived from them.
CSV (reader CSV_1)
    attributes: filecode text, region_v024 text, total_children_RegionCount text, total_young_RegionCount text, fever_occurrence_RegionCount text, fever_full_treat_RegionCount text, fever_any_treat_RegionCount text, fever_occurrence_RegionProp text, fever_full_treat_RegionProp text, young_full_treat_RegionProp text, fever_any_treat_RegionProp text, young_any_treat_RegionProp text
    -> StatisticsCalculator_2
StatisticsCalculator_2
    PREPEND_ATTR_NAME_CHOICE = For multiple results only
    STATS_ATTRS = fever_any_treat_RegionCount fever_full_treat_RegionCount fever_occurrence_RegionCount total_children_RegionCount total_young_RegionCount
    SUM_ATTR = _sum
    COMPUTE_HISTOGRAM = NO
    GROUP_BY = filecode
    SUMMARY -> AttributeCreator
AttributeCreator
    ATTR_LIST = fever_full_treat_TotalProp,@Evaluate(@Value(fever_full_treat_RegionCount._sum)/@Value(fever_occurrence_RegionCount._sum)),fever_any_treat_TotalProp,@Evaluate(@Value(fever_any_treat_RegionCount._sum)/@Value(fever_occurrence_RegionCount._sum)),fever_occurrence_TotalProp,@Evaluate(@Value(fever_occurrence_RegionCount._sum)/@Value(total_young_RegionCount._sum))
    -> StatisticsCalculator_2_Summary
    -> NationalSurveyResults_Weighted (writer CSV_2)
NationalSurveyResults_Weighted (writer CSV_2)
    attributes: filecode text, fever_any_treat_RegionCount._sum auto, fever_full_treat_RegionCount._sum auto, fever_occurrence_RegionCount._sum auto, total_children_RegionCount._sum auto, total_young_RegionCount._sum auto, fever_full_treat_TotalProp auto, fever_any_treat_TotalProp auto, fever_occurrence_TotalProp auto
StatisticsCalculator_2_Summary: Inspector
