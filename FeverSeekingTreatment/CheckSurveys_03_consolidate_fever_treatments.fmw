FME workspace CheckSurveys_03_consolidate_fever_treatments.fmw

Parameters:
- DestDataset_CSV = C:\Users\zool1301\Documents\DHS\Scrape\Info   # Destination CSV (CommaSeparatedValue) Folder
- SourceDataset_CSV_5 = C:\Users\zool1301\Documents\DHS\Scrape\Info\SurveysInEndemicCountries.csv   # Source CSV (CommaSeparatedValue) File(s)
- SourceDataset_CSV_2 = $(FME_MF_DIR)Info\Merged H32 BM KB.csv   # Source CSV (CommaSeparatedValue) File(s)

Readers:
- CSV_1: CSV from $(SourceDataset_CSV_5)
- CSV_2: CSV from $(SourceDataset_CSV_2)

Writers:
- CSV_3: CSV to $(DestDataset_CSV)

Note: This workbench generates the H32 question-flagging table. It reads a CSV of all the surveys to be processed (Generated in step 2) and based on these reads the REC43 table of those surveys (the path in the FeatureReader will need amending to run on another PC). / It then outputs the identifier (e.g. H32A) and the label of each H32* question from each survey into a single collated file. This is then passed to an actual Scientist and they have to Do Some Work, by flagging in the output column whether the question, based on the text, should be interpreted as seeking "proper" treatment and / or "any" treatment. The workbench makes its own cute little guess based on whether the question mentions any key words like "hospital", but that probably isn't very useful. / It also reads in an earlier edition of the question-flagging table, and copies over the answers from that if they exist. This would come in useful if, for example, the Scientist decides after doing the Work once to identify "proper" treatment, that they also want to ask about "any" treatment, so that they don't have to flag all the "proper" treatment questions again. / The flagged output, when received back, will be used to run the actual data extraction workspace.
SurveysInEndemicCountries (reader CSV_1)
    attributes: FileCode char(11), Country char(26), Year char(8), Survey_ID_num number(4,0), CountryCodeShort char(3)
    -> AttributeCreator_5
AttributeCreator_5
    ATTR_LIST = parsedREC43path,C:\Users\zool1301\Documents\DHS\Scrape\ParsedSpecs\@Value(FileCode).FlatRecordSpec.csv
    -> FeatureReader
FeatureReader
    CSV__STRIP_QUOTES = yes
    CSV__GROUP_BY_DATASET = no
    ATTRS_TO_EXPOSE = Name Label RecordName RecordTypeValue Start Len Occurrences FMETYPE
    FORMAT = CSV
    DATASET = @Value(parsedREC43path)
    CSV_SCAN_MAX_FEATURES = 1000
    CSV__IN_FIELD_NAMES = YES
    CSV__IN_SEPARATOR = ,
    COMBINE_GEOM = Use Result
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__FIELD_NAMES_AFTER_HEADER = no
    FEATURETYPES_RADIO = FEATURETYPES
    CSV__ALLOW_SPACES_IN_COLUMN_NAMES = yes
    OUTPUT_FEATURES_DISPLAY = Based on Connections
    CSV__DUPLICATE_DELIMS = no
    ATTR_CONFLICT_RES = Use Result
    ATTR_ACCUM_MODE = Merge Initiator and Result
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__SKIP_FOOTER = 0
    <OTHER> -> Tester
Tester
    TEST_DESCRIPTION = ""
    TEST_MODE = Automatic
    BOOL_OP = OR
    TEST_CLAUSE = TEST @Value(Name) BEGINS_WITH H32
    PASSED -> StringSearcher
StringSearcher
    MATCHED_PARTS_ATTR = _old_filecode
    MATCHED_RESULT_ATTR = _matched_characters
    CASE = no
    REGEXP = ^\d+\.(\w+)
    STRING_TO_SEARCH = @Value(FileCode)
    MATCHED -> ListIndexer
ListIndexer
    INDEX = 0
    LIST_ATTR = _old_filecode{}
    -> FeatureMerger [input 1]
Merged H32 BM KB (reader CSV_2)
    attributes: FileCode char(7), RecordName char(6), RecordTypeValue char(4), Name char(5), Label char(63), Start number(4,0), Len number(2,0), Occurrences char(1), FMETYPE char(12), CountAsTreatment_Initial char(4), BM_CountAsSeekedTreatment char(162), OUTPUT_CountAsTreatmentSought char(2), Note char(73), Any_Treat char(2)
    -> FeatureMerger [input 2]
FeatureMerger
    JOIN_KEYS = @Value(_old_filecode) @Value(FileCode) AUTO
    MERGE_TYPE = Attributes Only
    ATTR_CONFLICT_RES = Use Requestor
    IGNORE_NULLS = No
    SUPPLIERS_FIRST = No
    PROCESS_DUPS = No
    ATTR_ACCUM_MODE = Merge Supplier
    MERGED -> MergedH32_AllEndemic (writer CSV_3)
    NOT_MERGED -> TestFilter
    UNREFERENCED -> FeatureMerger_Unreferenced
    NOT_MERGED -> FeatureMerger_NotMerged
TestFilter
    TEST_LIST:
      BOOL_OP,OR,COMPOSITE_TEST,<Unused>,TEST_CLAUSE,"TEST @LowerCase(@Value(Label)) CONTAINS no treatment
      TEST @LowerCase(@Value(Label)) BEGINS_WITH na -
      TEST @Value(Label) ENDS_WITH NA",DefinitelyNo,BOOL_OP,OR,COMPOSITE_TEST,<Unused>,TEST_CLAUSE,"TEST @LowerCase(@Value(Label)) CONTAINS homeopathic
      TEST @LowerCase(@Value(Label)) CONTAINS no treatment
      TEST @LowerCase(@Value(Label)) CONTAINS shop
      TEST @LowerCase(@Value(Label)) CONTAINS market
      TEST @LowerCase(@Value(Label)) CONTAINS traditional
      TEST @LowerCase(@Value(Label)) CONTAINS friend
      TEST @LowerCase(@Value(Label)) CONTAINS church
      TEST @LowerCase(@Value(Label)) CONTAINS kiosk
      TEST @LowerCase(@Value(Label)) CONTAINS religious
      TEST @LowerCase(@Value(Label)) BEGINS_WITH na -
      TEST @Value(Label) ENDS_WITH NA",ProbablyNo,BOOL_OP,OR,COMPOSITE_TEST,<Unused>,TEST_CLAUSE,"TEST @LowerCase(@Value(Label)) CONTAINS hospital
      TEST @LowerCase(@Value(Label)) CONTAINS government
      TEST @LowerCase(@Value(Label)) CONTAINS ngo
      TEST @LowerCase(@Value(Label)) CONTAINS welfare",ProbablyYes
    DEFAULT_VALUE = DontKnow
    ProbablyNo -> AttributeCreator
    ProbablyYes -> AttributeCreator_2
    DontKnow -> AttributeCreator_3
    DefinitelyNo -> AttributeCreator_4
AttributeCreator_4
    ATTR_LIST = CountAsTreatmentGuess,No,AnyTreatmentGuess,No
AttributeCreator
    ATTR_LIST = CountAsTreatmentGuess,No,AnyTreatmentGuess,?
    -> MergedH32_AllEndemic (writer CSV_3)
AttributeCreator_2
    ATTR_LIST = CountAsTreatmentGuess,Yes,AnyTreatmentGuess,Yes
    -> MergedH32_AllEndemic (writer CSV_3)
AttributeCreator_3
    ATTR_LIST = CountAsTreatmentGuess,?,AnyTreatmentGuess,?
    -> MergedH32_AllEndemic (writer CSV_3)
MergedH32_AllEndemic (writer CSV_3)
    attributes: FileCode char(12), RecordName char(6), RecordTypeValue char(4), Name char(7), Label char(62), Start number(4,0), Len number(3,0), Occurrences char(1), FMETYPE char(13), CountAsTreatmentGuess char(3), Note char(100), AnyTreatmentGuess char(3), Any_Treat char(3), OUTPUT_CountAsTreatmentSought char(3)
FeatureMerger_NotMerged: Inspector
FeatureMerger_Unreferenced: Inspector
