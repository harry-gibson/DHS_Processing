FME workspace summarise_ACT_and_other_AM.fmw

Parameters:
- REC01_CSV = C:\Users\zool1301\Documents\DHS\Phase6\ExtractedSurveyRecords_Python\NMIR60.REC01.csv   # Survey CSV for REC01
- REC21_CSV = C:\Users\zool1301\Documents\DHS\Phase6\ExtractedSurveyRecords_Python\NMIR60.REC21.csv   # Survey CSV for REC21
- REC43_CSV = C:\Users\zool1301\Documents\DHS\Phase6\ExtractedSurveyRecords_Python\NMIR60.REC43.csv   # Survey CSV for REC43
- RECML_CSV = C:\Users\zool1301\Documents\DHS\Phase6\ExtractedSurveyRecords_Python\NMIR60.RECML.csv   # Survey CSV for RECML
- RECH0_CSV = C:\Users\zool1301\Documents\DHS\Phase6\ExtractedSurveyRecords_Python\NMIR60.RECH0.csv   # Survey CSV for RECH0
- RECH1_CSV = C:\Users\zool1301\Documents\DHS\Phase6\ExtractedSurveyRecords_Python\NMIR60.RECH1.csv   # Survey CSV for RECH1
- REC11_CSV = C:\Users\zool1301\Documents\DHS\Phase6\ExtractedSurveyRecords_Python\NMIR60.REC11.csv   # Survey CSV for REC11
- MaxAge = 5   # Children less than or equal to age (yrs)
- SurveyRecordSpec = C:\Users\zool1301\Documents\DHS\Phase6\SurveySpecs_Final\NMIR60.FlatRecordSpec.csv   # Record spec file for survey (Generated with python script)
- DestDataset_FILEGDB = $(FME_MF_DIR)Outputs\Phase6_ACT_Test.gdb   # Destination Geodatabase for geographic (point and region) data
- AllPointShapes = C:\Users\zool1301\Documents\DHS\Phase6\ExtractedSurveysAndShapes\*.shp   # All survey point shapefiles
- OutCSVDir = $(FME_MF_DIR)Outputs   # Destination CSV Folder for tablular results
- SURVEY_GPS_FEAT_TYPE = NMGE61FL
- SurveyIDMap_CSV = C:\Users\zool1301\Documents\DHS\DHS_Info\SurveyIdsByFile_P6_All.csv   # Survey ID mapping CSV file
- Source_GDB_Boundaries = C:\Users\zool1301\Documents\DHS\DHS_Info\DHS_Boundary_Data\full_download\sdr_subnational_boundaries_all_surveys.gdb   # Source Geodatabase containing survey boundaries
- Use_ARI = 0   # Use ARI fields (H31*) in addition to H22
- DestDataset_GEODATABASE_FILE = $(FME_MF_DIR)Outputs\Phase6_ACT_Test_AO.gdb   # Destination Esri File Geodatabase
- VariableSelectionXLS = $(FME_MF_DIR)SupportingData\variable_selection_full.xlsx   # Excel file specifying which variables to count as which treatment
- DestDataset_CSV = C:\Users\zool1301\Documents   # Destination CSV (CommaSeparatedValue) Folder
- RECH2_CSV = C:\Users\zool1301\Documents\DHS\Acquisition\20150626_FullSiteScrape\ProcessedTables\363.NMIR61.RECH2.csv   # RECH2 (HouseholdCharacteristics) CSV

Readers:
- CSV_1: CSV from $(REC21_CSV)
- CSV_2: CSV from $(REC43_CSV)
- CSV_3: CSV from $(REC01_CSV)
- CSV_4: CSV from $(RECML_CSV)
- CSV_5: CSV from $(RECH1_CSV)
- CSV_6: CSV from $(RECH0_CSV)
- CSV_7: CSV from $(REC11_CSV)
- CSV_8: CSV from $(SurveyRecordSpec)
- SHAPE_1: SHAPE from $(AllPointShapes)
- SHAPE_2: SHAPE from $(AllPointShapes)
- FILEGDB_1: FILEGDB from $(Source_GDB_Boundaries)
- CSV_9: CSV from $(SurveyIDMap_CSV)
- XLSXR_1: XLSXR from $(VariableSelectionXLS)
- CSV_12: CSV from $(RECH2_CSV)

Writers:
- FILEGDB_2: FILEGDB to $(DestDataset_FILEGDB)
- CSV_10: CSV to $(OutCSVDir)
- GEODATABASE_FILE_1: GEODATABASE_FILE to $(DestDataset_GEODATABASE_FILE)
- CSV_11: CSV to $(DestDataset_CSV)

Note: TODO / - Check fever stats grouping in old work (should have included BIDX I think!) / - Add output columns / - Add education (where from?)
CollateChildLines: AttributeRemover
    -> FeatureMerger [input 2]
Note: Normalise / Format the multi-columns of the treament into a layout like / recode / _treatment_name / _treatment_value / ML13A / SP/Fansidar / 1 / In other words get the standardised name (as used in spreadsheet header) for each relevant recode in this particular survey- we will later be able to group by this column to summarise the amount of each type of treatment
AttributeKeeper_10
    KEEP_ATTRS = Amodiaquine,Artemether,Artemisinin,Artesunate,Chloroquine,Combination of Chloroquine and Fansidar (Homapak),Mefloquine,Other anti-malarial,Primaquine,Quinine,SP/Fansidar,recode
    -> AttributeExploder_2
AttributeExploder_2
    ATTR_VALUE_LABEL = _treatment_value
    ATTR_NAME_LABEL = _treatment_name
    EXPLODING_TYPE = Features
    KEEP_GEOMETRY = No
    KEEP_ATTRIBUTES = Yes
    -> AttributeKeeper_9
AttributeKeeper_9
    KEEP_ATTRS = recode,_treatment_name,_treatment_value
    -> AttributeValueMapper_2
AttributeValueMapper_2
    SRC = _treatment_value
    DIRECTION = Forward (Source To Destination)
    LUT = Y,1,y,1
    DEFAULT_VALUE = 0
    VAL_ATTR = _treatment_value
    -> Tester_5
Tester_5
    TEST_MODE = Automatic
    BOOL_OP = OR
    TEST_DESCRIPTION = ""
    TEST_CLAUSE = TEST @Value(_treatment_value) = 1
    PASSED -> FeatureMerger_11 [input 2]
Note: For each yes answer, see if it was to a question about ACT taken by matching on question id (RECODE)
FeatureMerger_4
    MERGE_TYPE = Attributes Only
    SUPPLIERS_FIRST = No
    PROCESS_DUPS = No
    ATTR_ACCUM_MODE = Merge Supplier
    JOIN_KEYS = @Value(_attr_name) @Value(recode) AUTO
    ATTR_CONFLICT_RES = Use Requestor
    IGNORE_NULLS = No
    MERGED -> Sampler
Note: take the first expldoed feature (i.e. yes-answered question) we find for each original feature (identified by CASEID and BIDX) (they all have all fields of the original unexploded feature too) / For ACT there should only be one question defining this so more than one postiive answer is an error
Sampler
    GROUP_BY = CASEID BIDX
    RATE = 1
    SAMPLE_TYPE_LONG = First N Features
    SAMPLED -> AttributeRemover
    NOT_SAMPLED -> Terminator_2
Terminator_2
    MESSAGE = Translation Terminated
Note: Remove the crud and that's our filtered ACT output for this sickness record
AttributeRemover
    REMOVE_ATTRS = _attr_name,_attr_value
    -> StatisticsCalculator_6
Note: summarise, i.e. count total ill kids who took ACT, by woman (CASEID)
StatisticsCalculator_6
    PREPEND_ATTR_NAME_CHOICE = For multiple results only
    COUNT_ATTR = fever_took_ACT
    COMPUTE_HISTOGRAM = NO
    GROUP_BY = CASEID
    STATS_ATTRS = BIDX
    SUMMARY -> CollateChildLines_2
Note: For each yes answer, see if it was to a question about ACT timing
FeatureMerger_9
    MERGE_TYPE = Attributes Only
    SUPPLIERS_FIRST = No
    PROCESS_DUPS = No
    ATTR_ACCUM_MODE = Merge Supplier
    JOIN_KEYS = @Value(_attr_name) @Value(recode) AUTO
    ATTR_CONFLICT_RES = Use Requestor
    IGNORE_NULLS = No
    MERGED -> Sampler_3
Sampler_3
    GROUP_BY = CASEID BIDX
    RATE = 1
    SAMPLE_TYPE_LONG = First N Features
    SAMPLED -> AttributeRemover_2
    NOT_SAMPLED -> Terminator_3
Note: For ACT timing there should only be one question defining this so more than one postiive answer is an error
Terminator_3
    MESSAGE = Translation Terminated
AttributeRemover_2
    REMOVE_ATTRS = _attr_name,_attr_value
    -> StatisticsCalculator_7
StatisticsCalculator_7
    PREPEND_ATTR_NAME_CHOICE = For multiple results only
    COUNT_ATTR = fever_took_ACT_quickly
    COMPUTE_HISTOGRAM = NO
    GROUP_BY = CASEID
    STATS_ATTRS = BIDX
    SUMMARY -> CollateChildLines_2
Note: For each yes answer, see if it was to a question about other antimalarial
FeatureMerger_10
    MERGE_TYPE = Attributes Only
    SUPPLIERS_FIRST = No
    PROCESS_DUPS = No
    ATTR_ACCUM_MODE = Merge Supplier
    JOIN_KEYS = @Value(_attr_name) @Value(recode) AUTO
    ATTR_CONFLICT_RES = Use Requestor
    IGNORE_NULLS = No
    MERGED -> Sampler_4
    MERGED -> FeatureMerger_11 [input 1]
Sampler_4
    GROUP_BY = CASEID BIDX
    RATE = 1
    SAMPLE_TYPE_LONG = First N Features
    SAMPLED -> AttributeRemover_3
    NOT_SAMPLED -> Children_With_More_Than_One_OtherAM
Note: take the first expldoed feature we find for each original feature (identified by CASEID and BIDX) / There can be more than one question meaning "is this an other antimalarial" so this just removes the duplicates / (they all have all fields of the original unexploded feature too so are redundant copies)
Children_With_More_Than_One_OtherAM: Inspector
AttributeRemover_3
    REMOVE_ATTRS = _attr_name,_attr_value
    -> StatisticsCalculator_8
StatisticsCalculator_8
    PREPEND_ATTR_NAME_CHOICE = For multiple results only
    COUNT_ATTR = fever_took_other_AM
    COMPUTE_HISTOGRAM = NO
    GROUP_BY = CASEID
    STATS_ATTRS = BIDX
    SUMMARY -> CollateChildLines_2
Note: For each yes answer, about other antimalarials, get the name of the antimalarial (as specified in the columns of the spreadsheet)
FeatureMerger_11
    MERGE_TYPE = Attributes Only
    SUPPLIERS_FIRST = No
    PROCESS_DUPS = No
    ATTR_ACCUM_MODE = Merge Supplier
    JOIN_KEYS = @Value(_attr_name) @Value(recode) AUTO
    ATTR_CONFLICT_RES = Use Requestor
    IGNORE_NULLS = No
    DUPLICATE_SUPPLIER -> Terminator
    MERGED -> AttributeRemover_4
AttributeRemover_4
    REMOVE_ATTRS = _attr_name,_attr_value
    -> AttributeKeeper_11
AttributeKeeper_11
    KEEP_ATTRS = _treatment_name,_treatment_value,CASEID,recode,BIDX
    -> AttributePivoter
Note: Summarise bywoman (CASEID) AND treatment name: this automatically generates one row for each woman (like statistics calculator) and one column for each treatment
AttributePivoter
    PIVOT_ATTR = _treatment_value
    ROW_GROUP_ATTRS = CASEID
    COLUMN_GROUP_ATTR = _treatment_name
    GROUP_TOTALS_TAG = Total
    PIVOT_SUMMARY_TYPES = Count
    DATA -> AttributePivoter_Data
    DATA -> AttributeExposer_2
Note: To work with the column attribs (i.e. treatment names) in the workbench we need to expose them otherwise they aren't known till runtime so we wouldn't be able to sum by cluster/region / This needs to be kept in sync with the names given in the spreadsheet column headers!
AttributeExposer_2
    ATTR_LIST = Amodiaquine,Artemether,Artemisinin,Artesunate,Chloroquine,"Combination of Chloroquine and Fansidar (Homapak)",Mefloquine,"Other anti-malarial",Primaquine,Quinine,SP/Fansidar
    -> CollateChildLines_2
CollateChildLines_2: AttributeRemover
    -> FeatureMerger [input 2]
AttributePivoter_Data: Inspector
Note: The recode-name mapping should be unique
Terminator
    MESSAGE = Spreadsheet specifies that the recode is two different types of treatment! Cannot interpret.
Note: Here we are not sampling. We want to retain all yes-answers to different antimalarials (a child could take more than one and we want to count them all)
Sampler_5 [off]
    GROUP_BY = CASEID BIDX
    RATE = 1
    SAMPLE_TYPE_LONG = First N Features
    NOT_SAMPLED -> Sampler_5_NotSampled
Sampler_5_NotSampled: Inspector [off]
CSV (reader CSV_12)
    attributes: HHID char(5), HV201 number(3,0), HV202 char(1), HV204 number(4,0), HV205 number(3,0), HV206 number(2,0), HV207 number(2,0), HV208 number(2,0), HV209 number(2,0), HV210 number(2,0), HV211 number(2,0), HV212 number(2,0), HV213 number(3,0), HV214 number(3,0), HV215 number(3,0), HV216 number(3,0), HV217 number(2,0), HV218 number(2,0), HV219 number(2,0), HV220 number(3,0), HV221 number(2,0), HV225 number(2,0), HV226 number(3,0), HV227 number(2,0), HV228 number(2,0), HV230A number(2,0), HV230B number(2,0), HV232 number(2,0), HV232B number(2,0), HV232C char(1),
      HV232D char(1), HV232E char(1), HV232Y number(2,0), HV234 char(1), HV234A number(2,0), HV235 number(2,0), HV236 char(1), HV237 number(2,0), HV237A number(2,0), HV237B number(2,0), HV237C number(2,0), HV237D number(2,0), HV237E char(1), HV237F number(2,0), HV237G char(1), HV237H char(1), HV237I char(1), HV237J char(1), HV237K char(1), HV237X number(2,0), HV237Z number(2,0), HV238 number(3,0), HV239 char(1), HV240 char(1), HV241 number(2,0), HV242 number(2,0), HV243A number(2,0), HV243B number(2,0), HV243C number(2,0), HV243D number(2,0),
      HV244 number(2,0), HV245 number(4,0), HV246 number(2,0), HV246A number(3,0), HV246B number(3,0), HV246C number(3,0), HV246D number(3,0), HV246E number(3,0), HV246F number(3,0), HV246G char(1), HV246H char(1), HV246I char(1), HV246J char(1), HV246K char(1), HV247 number(2,0), HV252 number(2,0), HV253 number(2,0), HV253A number(2,0), HV253B number(2,0), HV253C number(2,0), HV253D char(1), HV253E char(1), HV253F char(1), HV253G char(1), HV253H char(1), HV253X number(2,0), HV253Z number(2,0), HV270 number(2,0), HV271 number(8,0), HML1 number(2,0),
      HML1A number(2,0), HML2 number(2,0)
    -> AttributeKeeper_15
AttributeKeeper_15
    KEEP_ATTRS = HHID,HV270,HV271
    -> AttributeRenamer_7
AttributeRenamer_7
    ATTR_LIST = HV270,Wealth factor quintile,,HV271,Wealth factor decimal,
Kiddywinks (writer CSV_11)
    attributes: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

Bookmark: Parse record 01 - individual (woman) respondent
Note: CSV: REC01 [CSV]
CSV (reader CSV_3)
    attributes: V026 number(2,0), V029 number(2,0), V030 number(3,0), V031 number(3,0), V000 char(4), V034 number(2,0), V040 number(3,0), V042 number(2,0), V044 char(1), V032 number(2,0), V028 number(4,0), V027 number(2,0), V025 number(2,0), V024 number(2,0), V023 number(3,0), V022 number(3,0), V021 number(3,0), V020 number(2,0), V019A number(2,0), V019 number(3,0), V018 number(3,0), V017 number(5,0), V016 number(3,0), V015 number(2,0), V014 number(2,0), V012 number(3,0), V013 number(2,0), CASEID char(9), V001 number(3,0), V002 number(4,0),
      V003 number(3,0), V004 number(3,0), V005 number(7,0), V006 number(3,0), V007 number(5,0), V008 number(5,0), V009 number(3,0), V010 number(5,0), V011 number(5,0)
    -> AttributeKeeper
Note: keep on ly the variables we're interested in
AttributeKeeper
    KEEP_ATTRS = CASEID,V000,V001,V002,V012,V024,V007
    -> REC01
    -> AttributeRenamer_6
AttributeRenamer_6
    ATTR_LIST = V000,CtryCodePhase,,V001,ClusterNum,,V002,HouseholdNum,,V007,InterviewYr,,V012,RespondentAge,,V024,Region,
    -> FeatureMerger [input 1]
    -> FeatureMerger_12 [input 2]
REC01: Inspector [off]

Bookmark: Parse record 11 - individual (woman) responsent further info (Education)
Note: CSV: REC11 (Respondent's Basic Data Continued - for woman's education)
CSV (reader CSV_7)
    attributes: CASEID char(8), V101 number(3,0), V102 number(2,0), V103 char(1), V104 char(1), V105 char(1), V106 number(2,0), V107 number(2,0), V113 number(3,0), V115 number(4,0), V116 number(3,0), V119 number(2,0), V120 number(2,0), V121 number(2,0), V122 number(2,0), V123 number(2,0), V124 number(2,0), V125 number(2,0), V127 number(3,0), V128 number(3,0), V129 number(3,0), V130 number(3,0), V131 char(1), V133 number(3,0), V134 char(1), V135 number(2,0), V136 number(3,0), V137 number(2,0), V138 number(2,0), V139 number(3,0),
      V140 number(2,0), V141 char(1), V149 number(2,0), V150 number(3,0), V151 number(2,0), V152 number(3,0), V153 number(2,0), AWFACTT number(4,0), AWFACTU number(4,0), AWFACTR number(4,0), AWFACTE number(4,0), AWFACTW number(4,0), V155 number(2,0), V156 number(2,0), V157 number(2,0), V158 number(2,0), V159 number(2,0), V160 number(2,0), V161 number(3,0), V166 char(1), V167 number(3,0), V168 number(2,0), V190 number(2,0), V191 number(8,0), ML101 number(2,0)
    -> AttributeKeeper_14
AttributeKeeper_14
    KEEP_ATTRS = CASEID,V106
    -> AttributeRenamer_5
AttributeRenamer_5
    ATTR_LIST = V106,WomansEducationLevel,
    -> AttributeValueMapper_3
AttributeValueMapper_3
    SRC = WomansEducationLevel
    DIRECTION = Forward (Source To Destination)
    LUT = 0,Woman_Educ_None,1,Woman_Educ_Primary,2,Woman_Educ_Secondary,3,Woman_Educ_Higher
    DEFAULT_VALUE = Woman_Educ_Missing
    VAL_ATTR = EducationLevel
    -> FeatureMerger_12 [input 1]
FeatureMerger_12
    MERGE_TYPE = Attributes Only
    SUPPLIERS_FIRST = No
    PROCESS_DUPS = No
    ATTR_ACCUM_MODE = Merge Supplier
    JOIN_KEYS = @Value(CASEID) @Value(CASEID) AUTO
    ATTR_CONFLICT_RES = Use Requestor
    IGNORE_NULLS = No
    MERGED -> AttributePivoter_3
    MERGED -> AttributePivoter_4

Bookmark: Accumulate and summarise woman's education
AttributePivoter_3
    PIVOT_ATTR = CASEID
    ROW_GROUP_ATTRS = ClusterNum
    COLUMN_GROUP_ATTR = EducationLevel
    GROUP_TOTALS_TAG = Total
    PIVOT_SUMMARY_TYPES = Count
    DATA -> AttributeExposer_4
AttributeExposer_4
    ATTR_LIST = "Grand Total",Woman_Educ_None,Woman_Educ_Primary,Woman_Educ_Secondary,Woman_Educ_Higher,Woman_Educ_Missing
    -> AttributeCreator_6
AttributeCreator_6
    ATTR_LIST = Woman_Educ_Higher_ClusterProp,@Evaluate(@Value(Woman_Educ_Higher)/@Value(Grand Total)),Woman_Educ_Secondary_ClusterProp,@Evaluate(@Value(Woman_Educ_Secondary)/@Value(Grand Total)),Woman_Educ_Primary_ClusterProp,@Evaluate(@Value(Woman_Educ_Primary)/@Value(Grand Total)),Woman_Educ_None_ClusterProp,@Evaluate(@Value(Woman_Educ_None)/@Value(Grand Total)),Woman_Educ_Missing_ClusterProp,@Evaluate(@Value(Woman_Educ_Missing)/@Value(Grand Total))
    -> AttributeRemover_5
AttributeRemover_5
    REMOVE_ATTRS = Grand Total,WomansEducationLevel,CASEID,CtryCodePhase,EducationLevel,HouseholdNum,InterviewYr,Region,RespondentAge
    -> FeatureMerger_15 [input 2]
AttributePivoter_4
    PIVOT_ATTR = CASEID
    ROW_GROUP_ATTRS = Region
    COLUMN_GROUP_ATTR = EducationLevel
    GROUP_TOTALS_TAG = Total
    PIVOT_SUMMARY_TYPES = Count
    DATA -> AttributeExposer_5
AttributeExposer_5
    ATTR_LIST = "Grand Total",Woman_Educ_None,Woman_Educ_Primary,Woman_Educ_Secondary,Woman_Educ_Higher,Woman_Educ_Missing
    -> AttributeCreator_8
AttributeCreator_8
    ATTR_LIST = Woman_Educ_Higher_RegionProp,@Evaluate(@Value(Woman_Educ_Higher)/@Value(Grand Total)),Woman_Educ_Secondary_RegionProp,@Evaluate(@Value(Woman_Educ_Secondary)/@Value(Grand Total)),Woman_Educ_Primary_RegionProp,@Evaluate(@Value(Woman_Educ_Primary)/@Value(Grand Total)),Woman_Educ_None_RegionProp,@Evaluate(@Value(Woman_Educ_None)/@Value(Grand Total)),Woman_Educ_Missing_RegionProp,@Evaluate(@Value(Woman_Educ_Missing)/@Value(Grand Total))
    -> AttributeRemover_6
AttributeRemover_6
    REMOVE_ATTRS = CASEID,CtryCodePhase,EducationLevel,Grand Total,HouseholdNum,InterviewYr,RespondentAge,WomansEducationLevel,ClusterNum
    -> FeatureMerger_14 [input 2]

Bookmark: Parse record 21 - individual children
Note: CSV: REC21 [CSV]
CSV (reader CSV_1)
    attributes: B3 number(5,0), B2 number(5,0), B1 number(3,0), B0 number(2,0), BORD number(2,0), CASEID char(9), B16 number(3,0), BIDX number(2,0), B15 number(2,0), B13 number(2,0), B12 number(4,0), B11 number(4,0), B10 number(2,0), B9 number(2,0), B8 number(3,0), B7 number(4,0), B6 number(4,0), B5 number(2,0), B4 number(2,0)
    -> AttributeKeeper_2
AttributeKeeper_2
    KEEP_ATTRS = B5,B8,BIDX,BORD,CASEID
    -> Tester
Note: Child is alive?
Tester
    TEST_MODE = Automatic
    BOOL_OP = OR
    TEST_DESCRIPTION = ""
    TEST_CLAUSE = TEST @Value(B5) = 1
    PASSED -> StatisticsCalculator_3
    PASSED -> Tester_4
Note: count total live children (Any age) / by woman
StatisticsCalculator_3
    PREPEND_ATTR_NAME_CHOICE = For multiple results only
    COUNT_ATTR = total_children
    COMPUTE_HISTOGRAM = NO
    GROUP_BY = CASEID
    STATS_ATTRS = CASEID
    SUMMARY -> CollateChildLines
Note: Child is less than or equal specified age?
Tester_4
    TEST_MODE = Automatic
    BOOL_OP = OR
    TEST_DESCRIPTION = ""
    TEST_CLAUSE = TEST @Value(B8) <= $(MaxAge)
    PASSED -> StatisticsCalculator_5
    PASSED -> AttributeKeeper_4
Note: count total live young / children by woman
StatisticsCalculator_5
    PREPEND_ATTR_NAME_CHOICE = For multiple results only
    COUNT_ATTR = total_young_children
    COMPUTE_HISTOGRAM = NO
    GROUP_BY = CASEID
    STATS_ATTRS = CASEID
    SUMMARY -> CollateChildLines
AttributeKeeper_4
    KEEP_ATTRS = BIDX,CASEID
    -> FeatureMerger_3 [input 2]

Bookmark: Parse record 43 - illness incidents in children and RECML - malaria in children
Note: REC43: / Individual child health record
CSV (reader CSV_2)
    attributes: H12B number(2,0), H12C number(2,0), H12D number(2,0), H12E number(2,0), H12F number(2,0), H12G number(2,0), H12H number(2,0), H12I number(2,0), H12J number(2,0), H12K number(2,0), H12L number(2,0), H12M number(2,0), H12N number(2,0), H12O number(2,0), H12P number(2,0), H12Q char(1), H12R char(1), H12S number(2,0), H12T number(2,0), H12U number(2,0), H12V number(2,0), H12W char(1), H12X number(2,0), H12Y number(2,0), H12Z number(2,0), H13 number(2,0), H13B char(1), H14 number(2,0), H15 char(1), H15A char(1),
      H15B char(1), H15C char(1), H15D char(1), H15E char(1), H15F char(1), H15G char(1), H15H char(1), H15I char(1), H15J char(1), H15K char(1), H15L char(1), H15M char(1), H20 char(1), H21A char(1), H21 char(1), H22 number(2,0), H31 number(2,0), H31B number(2,0), H31C number(2,0), H31D number(2,0), H31E number(2,0), H32A number(2,0), H32B number(2,0), H32C number(2,0), H32D number(2,0), H32E number(2,0), H32F number(2,0), H32G number(2,0), H32H number(2,0), H32I number(2,0),
      H32J number(2,0), H32K number(2,0), H32L number(2,0), H32M number(2,0), H32N number(2,0), H32O number(2,0), H32P number(2,0), H32Q char(1), H32R char(1), H32S number(2,0), H32T number(2,0), H32U number(2,0), H32V number(2,0), H32W number(2,0), H32X number(2,0), H32Y number(2,0), H32Z number(2,0), H33 number(2,0), H33D number(3,0), H33M number(3,0), H33Y number(5,0), H34 number(2,0), H35 char(1), H36A number(2,0), H36B number(2,0), H36D number(2,0), H36E char(1), H36F char(1), H37A number(2,0), H37B number(2,0),
      H37C char(1), H37D number(2,0), H37E number(2,0), H37F char(1), H37G char(1), H37H number(2,0), H37I number(2,0), H37J number(2,0), H37K number(2,0), H37L number(2,0), H37M number(2,0), H37N number(2,0), H37O number(2,0), H37P number(2,0), H37X number(2,0), H37Y number(2,0), H37Z number(2,0), H38 number(2,0), H39 number(2,0), H40 char(1), H40D char(1), H40M char(1), H40Y char(1), H41A char(1), H41B char(1), H42 number(2,0), H43 number(2,0), H44A char(1), H44B char(1), H44C char(1),
      H45 char(1), H46A number(3,0), H46B char(1), H47 char(1), H5 number(2,0), HIDX number(2,0), H1 number(2,0), H2 number(2,0), H8D number(3,0), H2D number(3,0), H2M number(3,0), H2Y number(5,0), H3 number(2,0), H3D number(3,0), H3M number(3,0), H3Y number(5,0), H4 number(2,0), H4D number(3,0), H4M number(3,0), H4Y number(5,0), H12A number(2,0), H5D number(3,0), H5M number(3,0), H5Y number(5,0), H6 number(2,0), H6D number(3,0), H6M number(3,0), H6Y number(5,0), H7 number(2,0), H7D number(3,0),
      H7M number(3,0), H7Y number(5,0), H8 number(2,0), H0 number(2,0), H9Y number(5,0), H9M number(3,0), H9D number(3,0), H9 number(2,0), H8Y number(5,0), H8M number(3,0), H36C number(2,0), CASEID char(9), H0D number(2,0), H0M number(3,0), H0Y number(5,0), H10 number(2,0), H11 number(2,0), H11B number(2,0)
    -> AttributeKeeper_3
AttributeKeeper_3
    KEEP_ATTRS = CASEID,H22,H31,H31B,H31C,H32A,H32B,H32C,H32D,H32E,H32F,H32G,H32H,H32I,H32J,H32K,H32L,H32M,H32N,H32O,H32P,H32Q,H32R,H32S,H32T,H32U,H32V,H32W,H32X,H32Y,H32Z,HIDX
    -> Tester_2
Note: Currently only checking H22 as all surveys were found to cover it
Note: Had fever in last 2 weeks / OR, (Optionally IIF parameter set) / Had cough AND (short breath OR probs in chest)
Tester_2
    TEST_MODE = Automatic
    BOOL_OP = COMPOSITE
    TEST_DESCRIPTION = ""
    TEST_CLAUSE:
      TEST @Value(H22) = 1
      TEST @Value(H31) BETWEEN 1,7
      TEST @Value(H31B) BETWEEN 1,7
      TEST @Value(H31C) BETWEEN 1,7
      TEST $(Use_ARI) = 1
    COMPOSITE_TEST = "1 OR (5 AND 2 AND (3 OR 4))"
    PASSED -> FeatureMerger_3 [input 1]
Note: ensure that illness record pertains / to a child below specified age (which it will / if age=5 but may not if age < 5)
FeatureMerger_3
    MERGE_TYPE = Attributes Only
    SUPPLIERS_FIRST = No
    PROCESS_DUPS = No
    ATTR_ACCUM_MODE = Merge Supplier
    JOIN_KEYS = @Value(CASEID) @Value(CASEID) AUTO @Value(HIDX) @Value(BIDX) AUTO
    ATTR_CONFLICT_RES = Use Requestor
    IGNORE_NULLS = No
    MERGED -> StatisticsCalculator
    NOT_MERGED -> IllnessRecordsChildTooOld
    MERGED -> AttributeKeeper_6
Note: count total ill children / by woman (CASEID)
StatisticsCalculator
    PREPEND_ATTR_NAME_CHOICE = For multiple results only
    COUNT_ATTR = fever_young
    COMPUTE_HISTOGRAM = NO
    GROUP_BY = CASEID
    STATS_ATTRS = CASEID
    SUMMARY -> CollateChildLines
AttributeKeeper_6
    KEEP_ATTRS = BIDX,CASEID,H22,HIDX
    -> FeatureMerger_8 [input 1]
IllnessRecordsChildTooOld: Inspector
Note: RECML: / Individual child malaria record
CSV (reader CSV_4)
    attributes: CASEID char(9), IDXML number(2,0), ML0 number(2,0), ML1 number(3,0), ML2 number(2,0), ML11 char(1), ML12 char(1), ML13A number(2,0), ML13B number(2,0), ML13C number(2,0), ML13D number(2,0), ML13E number(2,0), ML13F char(1), ML13G char(1), ML13H number(2,0), ML13I number(2,0), ML13J number(2,0), ML13K number(2,0), ML13L number(2,0), ML13M number(2,0), ML13N char(1), ML13O char(1), ML13P char(1), ML13X number(2,0), ML13Y number(2,0), ML13Z number(2,0), ML14A char(1), ML14B char(1), ML14Y char(1), ML14Z char(1),
      ML15A char(1), ML15B char(1), ML15C char(1), ML16A number(2,0), ML16B char(1), ML16C char(1), ML17A number(2,0), ML17B char(1), ML17C char(1), ML18A char(1), ML18B char(1), ML18C char(1), ML19A char(1), ML19B char(1), ML19C char(1), ML19D char(1), ML19E char(1), ML19F char(1), ML19X char(1), ML19Y char(1), ML19Z char(1), ML20A number(2,0), ML20B char(1), ML20C char(1), ML21A char(1), ML21B char(1), ML21C char(1), ML22A char(1), ML22B char(1), ML22C char(1),
      ML23A number(2,0), ML23B char(1), ML23C char(1), ML24C char(1)
    -> FeatureMerger_8 [input 2]
Note: Attach the malaria specific items to the child health record item
FeatureMerger_8
    MERGE_TYPE = Attributes Only
    SUPPLIERS_FIRST = No
    PROCESS_DUPS = No
    ATTR_ACCUM_MODE = Merge Supplier
    JOIN_KEYS = @Value(BIDX) @Value(IDXML) AUTO @Value(CASEID) @Value(CASEID) AUTO
    ATTR_CONFLICT_RES = Use Requestor
    IGNORE_NULLS = No
    MERGED -> AttributeExploder
Note: Separate each illness record into a new feature (record) for each of the variables (fields) that can define the treatment. i.e. normalise it so the features are now just Question Name / Question Answer pairs. (But keep the original attribs too for ease of flipping back to the input format later)
AttributeExploder
    ATTR_VALUE_LABEL = _attr_value
    ATTR_NAME_LABEL = _attr_name
    EXPLODING_TYPE = Features
    KEEP_GEOMETRY = No
    KEEP_ATTRIBUTES = Yes
    -> Tester_6
Note: Keep features corresponding to a question that was answered "yes" (no matter what the question was)
Tester_6
    TEST_MODE = Automatic
    BOOL_OP = OR
    TEST_DESCRIPTION = ""
    TEST_CLAUSE = TEST @Value(_attr_value) = 1
    PASSED -> FeatureMerger_4 [input 1]
    PASSED -> FeatureMerger_9 [input 1]
    PASSED -> FeatureMerger_10 [input 1]

Bookmark: Work out which of the antimalarial variables we want to look at to define treatment
Note: RecordSpec for the overall survey, / gives the survey-specific labels allocated to each H32* variable. Generated by the DCF parser. This info is now in the database so could be read from there. The only reason for reading it here now is to get the file (survey) code to filter the interpretation spreadsheet.
CSV (reader CSV_8)
    attributes: FileCode char(7), RecordName char(6), RecordTypeValue char(4), Name char(6), Label char(65), Start number(4,0), Len number(3,0), Occurrences char(1), FMETYPE char(13)
    -> VariableSetter
VariableSetter
    VALUE = @Value(FileCode)
    SCOPE = Global
    VARNAME = currentFileCode
    -> Sampler_2
Note: Simplify, remove all but RECODE id as we only want these to filter what comes through
AttributeKeeper_5
    KEEP_ATTRS = recode
    -> FeatureMerger_4 [input 2]
    -> AttributeKeeper_5_Output
AttributeKeeper_5_Output: Inspector [off]
AttributeKeeper_7
    KEEP_ATTRS = recode
    -> FeatureMerger_9 [input 2]
AttributeKeeper_8
    KEEP_ATTRS = recode
    -> FeatureMerger_10 [input 2]

Bookmark: Interpret antimalarial questions manually via external spreadsheet
Note: External spreadsheet has been generated containing all variable names / labels from the malaria table RECML. This has been manually flagged to indicate for each variable whether it should be interpreted as "ACT taken", "Other antimalarial taken", "ACT taken within 24 hours", if the data file contains a response to that question. It also contains further columns to identify questions relating to specific other antimalarials i.e. to pick out all questions relating to Quinine, etc.
Sampler_2
    GROUP_BY = FileCode
    RATE = 1
    SAMPLE_TYPE_LONG = First N Features
    SAMPLED -> FeatureMerger_5 [input 2]
Note: Spreadsheet specifying question interpretations
Sheet1 (reader XLSXR_1)
    attributes: survey char(7), record char(6), record name char(8), recode char(6), recode desc char(74), took ACT in first 24hrs of onset of fever char(2), ACT taken for fever char(2), took a non-ACT antimalarial for fever char(2), SP/Fansidar char(2), Chloroquine char(2), Amodiaquine char(2), Quinine char(2), Artesunate char(2), Artemisinin char(2), Artemether string, Combination of Chloroquine and Fansidar (Homapak) string, Mefloquine char(2), Primaquine char(2), Other anti-malarial char(2)
    -> FeatureMerger_5 [input 1]
Note: Get the ones relating to this survey
FeatureMerger_5
    MERGE_TYPE = Attributes Only
    SUPPLIERS_FIRST = Yes
    PROCESS_DUPS = No
    ATTR_ACCUM_MODE = Merge Supplier
    JOIN_KEYS = @Value(survey) @Value(FileCode) AUTO
    ATTR_CONFLICT_RES = Use Requestor
    IGNORE_NULLS = No
    MERGED -> Tester_7
Note: Does this variable represent an "ACT taken" question? (according to appropriate flag column)
Note: We should only have Y in 1 of these columns!
Tester_7
    TEST_MODE = Automatic
    BOOL_OP = OR
    TEST_DESCRIPTION = ""
    TEST_CLAUSE = TEST @LowerCase(@Value(ACT taken for fever)) = y
    PASSED -> AttributeKeeper_5
    FAILED -> Tester_8
Note: Does this variable represent an "ACT within 24 hrs of onset" question?
Tester_8
    TEST_MODE = Automatic
    BOOL_OP = OR
    TEST_DESCRIPTION = ""
    TEST_CLAUSE = TEST @LowerCase(@Value(took ACT in first 24hrs of onset of fever)) = y
    FAILED -> Tester_9
    PASSED -> AttributeKeeper_7
Note: Does this variable represent an "other antimalarial taken" question?
Tester_9
    TEST_MODE = Automatic
    BOOL_OP = OR
    TEST_DESCRIPTION = ""
    TEST_CLAUSE = TEST @LowerCase(@Value(took a non-ACT antimalarial for fever)) = y
    PASSED -> AttributeKeeper_8
    PASSED -> AttributeKeeper_10

Bookmark: Accumulate results by individual woman
Note: Attach each of the different child summaries to each woman. / Each has a different variable name so we allow multiple suppliers to attach them all
FeatureMerger
    MERGE_TYPE = Attributes Only
    SUPPLIERS_FIRST = No
    PROCESS_DUPS = Yes
    ATTR_ACCUM_MODE = Merge Supplier
    GEOM_TYPE = Build Polygons
    JOIN_KEYS = @Value(CASEID) @Value(CASEID) AUTO
    ATTR_CONFLICT_RES = Use Requestor
    IGNORE_NULLS = No
    MERGED -> AttributeCreator
    MERGED -> Tester_3
    MERGED -> StatisticsCalculator_4
    MERGED -> StatisticsCalculator_2

Bookmark: Accumulate and summarise child results by cluster (point location)
Note: summarise by cluster (V001), also grouping by country (V000) and region (V024) so that these carry thru
StatisticsCalculator_4
    SUM_ATTR = ClusterSum
    PREPEND_ATTR_NAME_CHOICE = For multiple results only
    COMPUTE_HISTOGRAM = NO
    GROUP_BY = ClusterNum CtryCodePhase Region
    STATS_ATTRS = Amodiaquine Artemether Artemisinin Artesunate Chloroquine Combination of Chloroquine and Fansidar (Homapak) fever_took_ACT fever_took_ACT_quickly fever_took_other_AM fever_young Mefloquine Other anti-malarial Primaquine Quinine SP/Fansidar total_children total_young_children
    SUMMARY -> BulkAttributeRenamer
Note: remove illegal chars from attribute names
BulkAttributeRenamer
    PATTERN_ACTION_DISP = Regular Expression Replace
    REPLACE_STR = _
    REPLACE_PATTERN = " |\\(|\\)|-|/|\\."
    ATTRCHOICE = All Attributes
    -> AttributeCreator_2
Note: Calculate proportional results from sums
AttributeCreator_2
    ATTR_LIST = fever_young_ClusterProp,@Evaluate(@Value(fever_young_ClusterSum)/@Value(total_young_children_ClusterSum)),fever_took_ACT_ClusterProp,@Evaluate(@Value(fever_took_ACT_ClusterSum)/@Value(fever_young_ClusterSum)),fever_took_ACT_quickly_ClusterProp,@Evaluate(@Value(fever_took_ACT_quickly_ClusterSum)/@Value(fever_young_ClusterSum)),fever_took_other_AM_ClusterProp,@Evaluate(@Value(fever_took_other_AM_ClusterSum)/@Value(fever_young_ClusterSum))
    -> AttributeRenamer
AttributeRenamer
    ATTR_LIST = Region,region_v024,,CtryCodePhase,ctry_phase,
    -> Results_by_cluster
    -> VariableRetriever
Results_by_cluster: Inspector
VariableRetriever
    SCOPE = Global
    VARNAME = currentFileCode
    VALUE_ATTR = filecode
    -> AttributeCreator_3
Note: Set output names for dynamic writers
AttributeCreator_3
    ATTR_LIST = outTableName,@Value(filecode)_ACT_By_Cluster_Table,outFCClusterName,@Value(filecode)_ACT_By_Cluster
    -> FeatureMerger_15 [input 1]
FeatureMerger_15
    MERGE_TYPE = Attributes Only
    SUPPLIERS_FIRST = No
    PROCESS_DUPS = Yes
    ATTR_ACCUM_MODE = Merge Supplier
    GEOM_TYPE = Build Polygons
    JOIN_KEYS = @Value(ClusterNum) @Value(ClusterNum) AUTO
    ATTR_CONFLICT_RES = Use Requestor
    IGNORE_NULLS = No
    MERGED -> FeatureMerger_2 [input 2]
    NOT_MERGED -> FeatureMerger_2 [input 2]
    MERGED -> File1 (writer CSV_10)
    NOT_MERGED -> File1 (writer CSV_10)
Note: Write CSV output results (always)
File1 (writer CSV_10)
    attributes: filecode text, region_v024 text, ClusterNum int, total_children_ClusterSum int, total_young_children_ClusterSum int, fever_young_ClusterSum int, fever_young_ClusterProp float, fever_took_ACT_ClusterProp float, fever_took_ACT_quickly_ClusterProp float, fever_took_other_AM_ClusterProp float, Amodiaquine_ClusterSum int, Artemether_ClusterSum int, Artemisinin_ClusterSum int, Artesunate_ClusterSum int, Chloroquine_ClusterSum int, Combination_of_Chloroquine_and_Fansidar__Homapak__ClusterSum int, Mefloquine_ClusterSum int, Other_anti_malarial_ClusterSum int, Primaquine_ClusterSum int, Quinine_ClusterSum int, SP_Fansidar_ClusterSum int, Head_Educ_None_ClusterProp float, Head_Educ_Primary_ClusterProp float, Head_Educ_Secondary_ClusterProp float, Head_Educ_Higher_ClusterProp float, Head_Educ_Missing_ClusterProp float, Woman_Educ_Higher_ClusterProp float, Woman_Educ_Secondary_ClusterProp float, Woman_Educ_Primary_ClusterProp float, Woman_Educ_None_ClusterProp float,
      Woman_Educ_Missing_ClusterProp float
Note: Read the points shapefile for the required survey if one exists
BDGE61FL (reader SHAPE_2)
    attributes: DHSID char(254), DHSCC char(254), DHSYEAR number(16,6), DHSCLUST number(16,6), CCFIPS char(254), ADM1FIPS char(254), ADM1FIPSNA char(254), ADM1SALBNA char(254), ADM1SALBCO char(254), ADM1DHS number(16,6), ADM1NAME char(254), DHSREGCO number(16,6), DHSREGNA char(254), SOURCE char(254), URBAN_RURA char(254), LATNUM number(16,6), LONGNUM number(16,6), ALT_GPS number(16,6), ALT_DEM number(16,6), DATUM char(254)
    -> AttributeExposer
AttributeExposer
    ATTR_LIST = fme_basename
    -> FeatureMerger_2 [input 1]
Note: NB / It is the responsibility of the user or caller to ensure the correct shapefile feature type name is provided. / The match is only done on cluster id which isn't unique between different surveys! A dummy value such as N/A must be provided if / no point shapefile is available otherwise it will read all!
FeatureMerger_2
    MERGE_TYPE = Attributes Only
    SUPPLIERS_FIRST = No
    PROCESS_DUPS = Yes
    ATTR_ACCUM_MODE = Merge Supplier
    GEOM_TYPE = Build Polygons
    JOIN_KEYS = @Value(DHSCLUST) @Value(ClusterNum) AUTO
    ATTR_CONFLICT_RES = Use Requestor
    IGNORE_NULLS = No
    MERGED -> Results_Points
    MERGED -> FeatureClass1 (writer FILEGDB_2)
    MERGED -> FeatureClass1 (writer GEODATABASE_FILE_1)
FeatureClass1 (writer GEODATABASE_FILE_1)
    attributes: filecode char(7), total_children_ClusterSum integer, total_young_children_ClusterSum integer, fever_young_ClusterSum integer, fever_young_ClusterProp double(20,10), fever_took_ACT_ClusterProp double(20,10), fever_took_ACT_quickly_ClusterProp double(20,10), fever_took_other_AM_ClusterProp double(20,10), region_v024 char(2048), ClusterNum integer, Amodiaquine_ClusterSum integer, Artemether_ClusterSum integer, Artemisinin_ClusterSum integer, Artesunate_ClusterSum integer, Chloroquine_ClusterSum integer, Combination_of_Chloroquine_and_Fansidar__Homapak__ClusterSum integer, Mefloquine_ClusterSum integer, Other_anti_malarial_ClusterSum integer, Primaquine_ClusterSum integer, Quinine_ClusterSum integer, SP_Fansidar_ClusterSum integer, Head_Educ_None_ClusterProp double, Head_Educ_Primary_ClusterProp double, Head_Educ_Secondary_ClusterProp double, Head_Educ_Higher_ClusterProp double, Head_Educ_Missing_ClusterProp double, Woman_Educ_None_ClusterProp double, Woman_Educ_Primary_ClusterProp double, Woman_Educ_Secondary_ClusterProp double, Woman_Educ_Higher_ClusterProp double,
      Woman_Educ_Missing_ClusterProp double
Results_Points: Inspector
Note: Write point featureclass results if any
FeatureClass1 (writer FILEGDB_2) [off]
    attributes: filecode text(12), total_children_ClusterSum int, total_young_children_ClusterSum int, fever_young_ClusterSum int, fever_young_ClusterProp double, fever_took_ACT_ClusterProp double, fever_took_ACT_quickly_ClusterProp double, fever_took_other_AM_ClusterProp double, region_v024 text(2048), ClusterNum int, Amodiaquine_ClusterSum int, Artemether_ClusterSum int, Artemisinin_ClusterSum int, Artesunate_ClusterSum int, Chloroquine_ClusterSum int, Combination_of_Chloroquine_and_Fansidar__Homapak__ClusterSum int, Mefloquine_ClusterSum int, Other_anti_malarial_ClusterSum int, Primaquine_ClusterSum int, Quinine_ClusterSum int, SP_Fansidar_ClusterSum int, Woman_Educ_Missing_Prop double, Woman_Educ_None_Prop double, Woman_Educ_ double

Bookmark: View or save individual results
AttributeCreator [off]
    ATTR_LIST = poorly_prop_by_woman,@Evaluate(@Value(fever_young_count)/@Value(total_young_count))
    -> ResultsByIndividual [off]
ResultsByIndividual: Inspector [off]

Bookmark: Individual summary check
Note: If total young count > 6 then health record doesn't / cover all children (there are a max of 6 health records)
Tester_3
    TEST_MODE = Automatic
    BOOL_OP = OR
    TEST_DESCRIPTION = ""
    TEST_CLAUSE = TEST @Value(total_young_children) > 6
    PASSED -> WarningNotAllHealthRecordsPresent
WarningNotAllHealthRecordsPresent: Inspector

Bookmark: Accumulate and summarise by region (polygon)
Note: summarise by region V024, also grouping by country V000 so that these carry thru
StatisticsCalculator_2
    SUM_ATTR = RegionSum
    PREPEND_ATTR_NAME_CHOICE = For multiple results only
    COMPUTE_HISTOGRAM = NO
    GROUP_BY = CtryCodePhase Region
    STATS_ATTRS = Amodiaquine Artemether Artemisinin Artesunate Chloroquine Combination of Chloroquine and Fansidar (Homapak) fever_took_ACT fever_took_ACT_quickly fever_took_other_AM fever_young Mefloquine Other anti-malarial Primaquine Quinine SP/Fansidar total_children total_young_children
    SUMMARY -> BulkAttributeRenamer_2
Note: remove illegal chars from attribute names
BulkAttributeRenamer_2
    PATTERN_ACTION_DISP = Regular Expression Replace
    REPLACE_STR = _
    REPLACE_PATTERN = " |\\(|\\)|-|/|\\."
    ATTRCHOICE = All Attributes
    -> AttributeCreator_4
Note: Calculate proportional results from sums
AttributeCreator_4
    ATTR_LIST = fever_young_RegionProp,@Evaluate(@Value(fever_young_RegionSum)/@Value(total_young_children_RegionSum)),fever_took_ACT_RegionProp,@Evaluate(@Value(fever_took_ACT_RegionSum)/@Value(fever_young_RegionSum)),fever_took_ACT_quickly_RegionProp,@Evaluate(@Value(fever_took_ACT_quickly_RegionSum)/@Value(fever_young_RegionSum)),fever_took_other_AM_RegionProp,@Evaluate(@Value(fever_took_other_AM_RegionSum)/@Value(fever_young_RegionSum))
    -> AttributeRenamer_2
AttributeRenamer_2
    ATTR_LIST = Region,region_v024,,CtryCodePhase,ctry_phase,
    -> VariableRetriever_2
VariableRetriever_2
    SCOPE = Global
    VARNAME = currentFileCode
    VALUE_ATTR = filecode
    -> AttributeCreator_7
Note: Set output name for dynamic writer
AttributeCreator_7
    ATTR_LIST = outFCRegionName,@Value(filecode)_ACT_By_Region
    -> FeatureMerger_6 [input 1]
Note: Read DHS survey identifier mapping file (provided by DHS and modified) to / work out which polygons are associated with this survey file
CSV (reader CSV_9)
    attributes: SurveyFilename char(7), Country char(22), Year char(8), Survey_ID_num number(4,0), SurveyAPI_ID char(10), Type char(4)
    -> FeatureMerger_6 [input 2]
Note: From the survey filename e.g. BDIR61 get the numeric DHS survey identifier as used in the regional boundaries
FeatureMerger_6
    MERGE_TYPE = Attributes Only
    SUPPLIERS_FIRST = No
    PROCESS_DUPS = No
    ATTR_ACCUM_MODE = Merge Supplier
    JOIN_KEYS = @LowerCase(@Value(filecode)) @LowerCase(@Value(SurveyFilename)) AUTO
    ATTR_CONFLICT_RES = Use Requestor
    IGNORE_NULLS = No
    MERGED -> FeatureMerger_7 [input 2]
    NOT_MERGED -> FeatureMerger_6_NotMerged
FeatureMerger_6_NotMerged: Inspector
Note: Read all DHS boundaries (downloaded and combined previously)
dhs_subnational_boundaries_all_surveys (reader FILEGDB_1)
    attributes: OBJECTID objectid, ISO text(2), FIPS text(2), DHSCC text(2), SVYTYPE text(3), SVYYEAR double, CNTRYNAMEE text(254), CNTRYNAMEF text(254), CNTRYNAMES text(254), DHSREGEN text(254), DHSREGFR text(254), DHSREGSP text(254), SVYID double, REG_ID text(15), Svy_Map text(3), MULTLEVEL text(3), LEVELRNK double, REGVAR text(254), REGCODE double, REGNAME text(254), OTHREGVAR text(254), OTHREGCO double, OTHREGNA text(254), LEVELCO text(254), LEVELNA text(254), REPALLIND text(254), REGNOTES text(254), SVYNOTES text(254), Shape_Length double, Shape_Area double
    -> FeatureMerger_7 [input 1]
Note: Attach results to boundaries by matching survey id
FeatureMerger_7
    MERGE_TYPE = Attributes Only
    SUPPLIERS_FIRST = No
    PROCESS_DUPS = No
    ATTR_ACCUM_MODE = Merge Supplier
    JOIN_KEYS = @Value(SVYID) @Value(Survey_ID_num) AUTO @Value(REGCODE) @Value(region_v024) AUTO
    ATTR_CONFLICT_RES = Use Requestor
    IGNORE_NULLS = No
    MERGED -> FeatureMerger_7_Merged
    MERGED -> FeatureMerger_14 [input 1]
Note: Attach results to boundaries by matching survey id
FeatureMerger_14
    MERGE_TYPE = Attributes Only
    SUPPLIERS_FIRST = No
    PROCESS_DUPS = Yes
    ATTR_ACCUM_MODE = Merge Supplier
    GEOM_TYPE = Build Polygons
    JOIN_KEYS = @Value(REGCODE) @Value(Region) AUTO
    ATTR_CONFLICT_RES = Use Requestor
    IGNORE_NULLS = No
    MERGED -> FeatureClass100 (writer FILEGDB_2)
    NOT_MERGED -> FeatureClass100 (writer FILEGDB_2)
Note: Write polygon featureclass results if any
FeatureClass100 (writer FILEGDB_2)
    attributes: filecode text(12), total_children_RegionSum int, total_young_children_RegionSum int, fever_young_RegionSum int, fever_young_RegionProp double, fever_took_ACT_RegionProp double, fever_took_ACT_quickly_RegionProp double, fever_took_other_AM_RegionProp double, region_v024 text(2048), Amodiaquine_RegionSum int, Artemether_RegionSum int, Artemisinin_RegionSum int, Artesunate_RegionSum int, Chloroquine_RegionSum int, Combination_of_Chloroquine_and_Fansidar__Homapak__RegionSum int, Mefloquine_RegionSum int, Other_anti_malarial_RegionSum int, Primaquine_RegionSum int, Quinine_RegionSum int, SP_Fansidar_RegionSum int, Head_Educ_None_RegionProp double, Head_Educ_Primary_RegionProp double, Head_Educ_Secondary_RegionProp double, Head_Educ_Higher_RegionProp double, Head_Educ_Missing_RegionProp double, Woman_Educ_None_RegionProp text(200), Woman_Educ_Primary_RegionProp text(200), Woman_Educ_Secondary_RegionProp text(200), Woman_Educ_Higher_RegionProp text(200), Woman_Educ_Missing_RegionProp text(200)
FeatureMerger_7_Merged: Inspector [off]

Bookmark: Accumulate and summarise head of household education by cluster / region
Note: Household schedule: read this to find the education of the head of household (can't just use REC01 women's as they may not be head of household)
CSV (reader CSV_5)
    attributes: HHID char(5), HVIDX number(3,0), HV101 number(3,0), HV102 number(2,0), HV103 number(2,0), HV104 number(2,0), HV105 number(3,0), HV106 char(1), HV107 char(1), HV108 char(1), HV109 char(1), HV110 char(1), HV111 char(1), HV112 char(1), HV113 char(1), HV114 char(1), HV115 char(1), HV116 char(1), HV117 number(2,0), HV118 char(1), HV120 number(2,0), HV121 char(1), HV122 char(1), HV123 char(1), HV124 char(1), HV125 char(1), HV126 char(1), HV127 char(1), HV128 char(1), HV129 char(1),
      HV130 char(1), HV131 char(1), HV132 char(1), HV133 char(1), HV134 char(1), HV135 char(1), HV136 char(1), HV137 char(1), HV138 char(1), HV139 char(1), HV140 char(1)
    -> AttributeKeeper_12
AttributeKeeper_12
    KEEP_ATTRS = HHID,HV106,HV108,HVIDX,HV101
    -> AttributeRenamer_4
AttributeRenamer_4
    ATTR_LIST = HVIDX,LineNum,,HV101,RelToHead,,HV106,HeadEducationLevel,,HV108,HeadEducationInYrs,
    -> Tester_10
Note: Find heads of households
Tester_10
    TEST_MODE = Automatic
    BOOL_OP = OR
    TEST_DESCRIPTION = ""
    TEST_CLAUSE = TEST @Value(RelToHead) = 1
    PASSED -> DuplicateRemover
DuplicateRemover
    KEYATTR = HHID
    UNIQUE -> AttributeValueMapper
    DUPLICATE -> MessageLogger
AttributeValueMapper
    SRC = HeadEducationLevel
    DIRECTION = Forward (Source To Destination)
    LUT = 0,Head_Educ_None,1,Head_Educ_Primary,2,Head_Educ_Secondary,3,Head_Educ_Higher
    DEFAULT_VALUE = Head_Educ_Missing
    VAL_ATTR = EducationLevel
    -> FeatureMerger_13 [input 1]
MessageLogger
    MESSAGE = A household was found with two heads! Chopped one off.
    TYPE = ERROR
Note: Household basic data: read this to get the cluster ID, via the line number, for the data in RECH1
CSV (reader CSV_6)
    attributes: HHID char(6), HV000 char(4), HV001 number(3,0), HV002 number(3,0), HV003 number(2,0), HV004 number(3,0), HV005 number(8,0), HV006 number(2,0), HV007 number(5,0), HV008 number(5,0), HV009 number(3,0), HV010 number(2,0), HV011 char(1), HV012 number(3,0), HV013 number(3,0), HV014 number(2,0), HV015 number(2,0), HV016 number(3,0), HV017 number(2,0), HV018 number(4,0), HV019 number(3,0), HV020 number(2,0), HV021 number(3,0), HV022 number(2,0), HV023 number(2,0), HV024 number(2,0), HV025 number(2,0), HV026 char(1), HV027 char(1), HV028 char(1),
      HV030 number(4,0), HV031 number(3,0), HV032 number(2,0), HV033 char(1), HV035 number(2,0), HV040 number(5,0), HV041 char(1), HV042 number(2,0), HV043 char(1), HV044 char(1)
    -> AttributeKeeper_13
AttributeKeeper_13
    KEEP_ATTRS = HHID,HV001,HV003,HV024,HV006,HV007
    -> AttributeRenamer_3
AttributeRenamer_3
    ATTR_LIST = HV001,ClusterNum,,HV003,RespondentLineNum,,HV024,Region,,HV006,MonthOfInterview,,HV007,YearOfInterview,
    -> FeatureMerger_13 [input 2]
FeatureMerger_13
    MERGE_TYPE = Attributes Only
    SUPPLIERS_FIRST = No
    PROCESS_DUPS = No
    ATTR_ACCUM_MODE = Merge Supplier
    JOIN_KEYS = @Value(HHID) @Value(HHID) AUTO
    ATTR_CONFLICT_RES = Use Requestor
    IGNORE_NULLS = No
    MERGED -> AttributePivoter_2
    MERGED -> AttributePivoter_5
AttributePivoter_2
    PIVOT_ATTR = HHID
    ROW_GROUP_ATTRS = ClusterNum
    COLUMN_GROUP_ATTR = EducationLevel
    GROUP_TOTALS_TAG = Total
    PIVOT_SUMMARY_TYPES = Count
    DATA -> AttributeExposer_3
AttributeExposer_3
    ATTR_LIST = "Grand Total",Head_Educ_None,Head_Educ_Primary,Head_Educ_Secondary,Head_Educ_Higher,Head_Educ_Missing
    -> AttributeCreator_5
AttributeCreator_5
    ATTR_LIST = Head_Educ_Higher_ClusterProp,@Evaluate(@Value(Head_Educ_Higher)/@Value(Grand Total)),Head_Educ_Secondary_ClusterProp,@Evaluate(@Value(Head_Educ_Secondary)/@Value(Grand Total)),Head_Educ_Primary_ClusterProp,@Evaluate(@Value(Head_Educ_Primary)/@Value(Grand Total)),Head_Educ_None_ClusterProp,@Evaluate(@Value(Head_Educ_None)/@Value(Grand Total)),Head_Educ_Missing_ClusterProp,@Evaluate(@Value(Head_Educ_Missing)/@Value(Grand Total))
    -> AttributeRemover_7
AttributeRemover_7
    REMOVE_ATTRS = EducationLevel,Grand Total,HHID,Region,RelToHead,RespondentLineNum,LineNum
    -> FeatureMerger_15 [input 2]
AttributePivoter_5
    PIVOT_ATTR = HHID
    ROW_GROUP_ATTRS = Region
    COLUMN_GROUP_ATTR = EducationLevel
    GROUP_TOTALS_TAG = Total
    PIVOT_SUMMARY_TYPES = Count
    DATA -> AttributeExposer_6
AttributeExposer_6
    ATTR_LIST = "Grand Total",Head_Educ_None,Head_Educ_Primary,Head_Educ_Secondary,Head_Educ_Higher,Head_Educ_Missing
    -> AttributeCreator_9
AttributeCreator_9
    ATTR_LIST = Head_Educ_Higher_RegionProp,@Evaluate(@Value(Head_Educ_Higher)/@Value(Grand Total)),Head_Educ_Secondary_RegionProp,@Evaluate(@Value(Head_Educ_Secondary)/@Value(Grand Total)),Head_Educ_Primary_RegionProp,@Evaluate(@Value(Head_Educ_Primary)/@Value(Grand Total)),Head_Educ_None_RegionProp,@Evaluate(@Value(Head_Educ_None)/@Value(Grand Total)),Head_Educ_Missing_RegionProp,@Evaluate(@Value(Head_Educ_Missing)/@Value(Grand Total))
    -> AttributeRemover_8
AttributeRemover_8
    REMOVE_ATTRS = ClusterNum,EducationLevel,Grand Total,HHID,LineNum,RelToHead,RespondentLineNum
    -> FeatureMerger_14 [input 2]

Bookmark: New Bookmark
Note: We were asked after initial development to pick out several more antimalarial specific variables for summary. We could repeat the above approach for each but as there are 15+ the workbench would become quite large. / Hence for the remainder we use a different approach, using an AttributePivoter to generate all the output columns

Bookmark: Summarise relevant yes-answers
Note: Process questions that were answered yes to see if they are the questions we have determined that we're interested in.

FME custom transformer DateDifferenceCalculator_2
Calculates the difference in time between two dates.
Select Start Date Attribute, End Date Attribute and input date format string. See DateFormatter documentation for more detailed explanations of date format strings.
Also select the units you wish the time difference to be expressed in. Time Difference will be stored in _TimeDifference attribute.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTR =   # " " Start Date
- SRC_ATTR_2 =   # " " End Date
- FMT = %Y%m%d   # Input Date Format
- Unit = 86400   # Output Time Units

INPUT (input)
    -> AttributeCreator
Note: Retrieve parameters
AttributeCreator
    NUM_SUBSEQUENT_FEATURES = 0
    NUM_PRIOR_FEATURES = 0
    ATTR_LIST = DDC_StartDate,@Value($(SRC_ATTR)),DDC_EndDate,@Value($(SRC_ATTR_2))
    -> DateFormatter
Note: Convert temp Date Attributes / to seconds since UNIX Epoch
DateFormatter
    FMT = %s
    DATE_ATTR = DDC_StartDate,DDC_EndDate
    SRCFMT = $(FMT)
    -> ExpressionEvaluator
Note: Subtract Dates and / convert to desired unit
ExpressionEvaluator
    EXPRESSION = @round(1.0*(@Value(DDC_EndDate)-@Value(DDC_StartDate))/$(Unit))
    VAL_ATTR = _TimeDifference
    -> AttributeRemover
Note: Remove temp attributes
AttributeRemover
    REMOVE_ATTRS = DDC_StartDate,DDC_EndDate
    -> OUTPUT (output)
OUTPUT (output)
