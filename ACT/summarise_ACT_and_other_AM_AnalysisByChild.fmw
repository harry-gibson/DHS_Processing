FME workspace summarise_ACT_and_other_AM_AnalysisByChild.fmw

Parameters:
- REC01_CSV = C:\Users\zool1301\Documents\DHS\Processing_Round1\Phase6\ExtractedSurveyRecords_Python\RWIR6Q.REC01.csv   # Survey CSV for REC01
- REC11_CSV = C:\Users\zool1301\Documents\DHS\Processing_Round1\Phase6\ExtractedSurveyRecords_Python\RWIR6Q.REC11.csv   # Survey CSV for REC11
- REC21_CSV = C:\Users\zool1301\Documents\DHS\Processing_Round1\Phase6\ExtractedSurveyRecords_Python\RWIR6Q.REC21.csv   # Survey CSV for REC21
- REC43_CSV = C:\Users\zool1301\Documents\DHS\Processing_Round1\Phase6\ExtractedSurveyRecords_Python\RWIR6Q.REC43.csv   # Survey CSV for REC43
- RECML_CSV = C:\Users\zool1301\Documents\DHS\Processing_Round1\Phase6\ExtractedSurveyRecords_Python\RWIR6Q.RECML.csv   # Survey CSV for RECML
- RECH0_CSV = C:\Users\zool1301\Documents\DHS\Processing_Round1\Phase6\ExtractedSurveyRecords_Python\RWIR6Q.RECH0.csv   # Survey CSV for RECH0
- RECH1_CSV = C:\Users\zool1301\Documents\DHS\Processing_Round1\Phase6\ExtractedSurveyRecords_Python\RWIR6Q.RECH1.csv   # Survey CSV for RECH1
- RECH2_CSV = C:\Users\zool1301\Documents\DHS\Processing_Round1\Phase6\ExtractedSurveyRecords_Python\RWIR6Q.RECH2.csv   # RECH2 (HouseholdCharacteristics) CSV
- MaxAge = 5   # Children less than or equal to age (yrs)
- SurveyIDMap_CSV = C:\Users\zool1301\Documents\DHS\DHS_Info\SurveyIdsByFile_P6_All.csv   # Survey ID mapping CSV file
- SurveyRecordSpec = C:\Users\zool1301\Documents\DHS\Processing_Round1\Phase6\SurveySpecs_Final\RWIR6Q.FlatRecordSpec.csv   # Record spec file for survey (Generated with python script)
- VariableSelectionXLS = $(FME_MF_DIR)SupportingData\variable_selection_full.xlsx   # Excel file specifying which variables to count as which treatment
- AllPointShapes = C:\Users\zool1301\Documents\DHS\Processing_Round1\Phase6\ExtractedSurveysAndShapes\GAGE61FL.shp   # All survey point shapefiles
- SURVEY_GPS_FEAT_TYPE = N/A
- Source_GDB_Boundaries = C:\Users\zool1301\Documents\DHS\DHS_Info\DHS_Boundary_Data\full_download\sdr_subnational_boundaries_all_surveys.gdb   # Source Geodatabase containing survey boundaries
- OutGDB_Name = $(FME_MF_DIR)Outputs\Phase6_ACT.gdb   # Destination Geodatabase for geographic (point and region) data
- OutCSVDir = $(FME_MF_DIR)Outputs\CSV_ACT   # Destination CSV Folder for tablular results
- Use_ARI = 0   # Use ARI fields (H31*) in addition to H22
- DestDataset_GEODATABASE_FILE = $(FME_MF_DIR)Outputs\Phase6_ACT_Test_AO.gdb   # UNUSED_Destination Esri File Geodatabase

Readers:
- CSV_1: CSV from $(REC21_CSV)
- CSV_2: CSV from $(REC43_CSV)
- CSV_3: CSV from $(REC01_CSV)
- CSV_4: CSV from $(RECML_CSV)
- CSV_5: CSV from $(RECH1_CSV)
- CSV_6: CSV from $(RECH0_CSV)
- CSV_7: CSV from $(REC11_CSV)
- CSV_8: CSV from $(SurveyRecordSpec)
- SHAPE_1: SHAPE from $(AllPointShapes)
- SHAPE_2: SHAPE from $(AllPointShapes)
- FILEGDB_1: FILEGDB from $(Source_GDB_Boundaries)
- CSV_9: CSV from $(SurveyIDMap_CSV)
- XLSXR_1: XLSXR from $(VariableSelectionXLS)
- CSV_10: CSV from $(RECH2_CSV)

Writers:
- FILEGDB_2: FILEGDB to $(OutGDB_Name)
- CSV_11: CSV to $(OutCSVDir)
- GEODATABASE_FILE_1: GEODATABASE_FILE to $(DestDataset_GEODATABASE_FILE)
- CSV_12: CSV to $(OutCSVDir)

Note: TODO / - Check fever stats grouping in old work (should have included BIDX I think!) / - Add output columns / - Add education (where from?)
Note: Separate each illness record into a new feature (record) for each of the variables (fields) that can define the treatment. i.e. normalise it so the features are now just Question Name / Question Answer pairs. (But keep the original attribs too for ease of flipping back to the input format later)
AttributeExploder
    ATTR_NAME_LABEL = _attr_name
    KEEP_GEOMETRY = No
    ATTR_VALUE_LABEL = _attr_value
    KEEP_ATTRIBUTES = Yes
    EXPLODING_TYPE = Features
    -> Tester_6
Note: Keep features corresponding to a question that was answered "yes" (no matter what the question was)
Tester_6
    TEST_CLAUSE = TEST @Value(_attr_value) = 1
    BOOL_OP = OR
    TEST_DESCRIPTION = ""
    TEST_MODE = Automatic
    PASSED -> FeatureMerger_4 [input 1]
    PASSED -> FeatureMerger_9 [input 1]
    PASSED -> FeatureMerger_10 [input 1]
Note: For each yes answer, see if it was to a question about ACT taken by matching on question id (RECODE)
FeatureMerger_4
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(_attr_name) @Value(recode) AUTO
    MERGED -> Sampler
Note: take the first expldoed feature (i.e. yes-answered question) we find for each original child feature (identified by ChildID) (they all have all fields of the original unexploded feature too) / For ACT there should only be one question defining this so more than one postiive answer is an error
Sampler
    RATE = 1
    SAMPLE_TYPE_LONG = First N Features
    GROUP_BY = ChildIDX
    SAMPLED -> AttributeRemover
    NOT_SAMPLED -> Terminator_2
    NOT_SAMPLED -> Warning_More_Than_One_ACT_Type
Warning_More_Than_One_ACT_Type: Inspector
Terminator_2 [off]
    MESSAGE = Translation Terminated
Note: Remove the crud and that's our filtered ACT output for this sickness record
AttributeRemover
    REMOVE_ATTRS = _attr_name,_attr_value
    -> StatisticsCalculator_6
Note: This was to summarise by WOMAN but they changed their mind and only want it by child now. So now we summarise by CHILD and so this really only removes attributes.
StatisticsCalculator_6
    COUNT_ATTR = FeverTookACT
    GROUP_BY = ChildIDX
    STATS_ATTRS = ChildIDX
    PREPEND_ATTR_NAME_CHOICE = For multiple results only
    COMPUTE_HISTOGRAM = NO
    SUMMARY -> CollateChildLines_2
Note: For each yes answer, see if it was to a question about ACT timing
FeatureMerger_9
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(_attr_name) @Value(recode) AUTO
    MERGED -> Sampler_3
Sampler_3
    RATE = 1
    SAMPLE_TYPE_LONG = First N Features
    GROUP_BY = ChildIDX
    SAMPLED -> AttributeRemover_2
    NOT_SAMPLED -> Terminator_3
    NOT_SAMPLED -> Warning_More_Than_One_ACT_Timing
Warning_More_Than_One_ACT_Timing: Inspector
Note: For ACT timing there should only be one question defining this so more than one postiive answer is an error
Terminator_3 [off]
    MESSAGE = Translation Terminated
AttributeRemover_2
    REMOVE_ATTRS = _attr_name,_attr_value
    -> StatisticsCalculator_7
StatisticsCalculator_7
    COUNT_ATTR = FeverTookACTQuickly
    GROUP_BY = ChildIDX
    STATS_ATTRS = ChildIDX
    PREPEND_ATTR_NAME_CHOICE = For multiple results only
    COMPUTE_HISTOGRAM = NO
    SUMMARY -> CollateChildLines_2
Note: For each yes answer, see if it was to a question about other antimalarial
FeatureMerger_10
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(_attr_name) @Value(recode) AUTO
    MERGED -> Sampler_4
    MERGED -> FeatureMerger_11 [input 1]
Sampler_4
    RATE = 1
    SAMPLE_TYPE_LONG = First N Features
    GROUP_BY = ChildIDX
    SAMPLED -> AttributeRemover_3
    NOT_SAMPLED -> Children_With_More_Than_One_OtherAM
AttributeRemover_3
    REMOVE_ATTRS = _attr_name,_attr_value
    -> StatisticsCalculator_8
StatisticsCalculator_8
    COUNT_ATTR = FeverTookOtherAM
    GROUP_BY = ChildIDX
    STATS_ATTRS = ChildIDX
    PREPEND_ATTR_NAME_CHOICE = For multiple results only
    COMPUTE_HISTOGRAM = NO
    SUMMARY -> CollateChildLines_2
Note: take the first expldoed feature we find for each original feature (identified by CHILDID) / There can be more than one question meaning "is this an other antimalarial" so this just removes the duplicates / (they all have all fields of the original unexploded feature too so are redundant copies)
Children_With_More_Than_One_OtherAM: Inspector [off]
Note: Gather all illness / health info
CollateChildLines_2: AttributeRemover
    -> FeatureMerger [input 2]
SubstringExtractor_2
    RESULT_ATTR = _CaseID_Idx_Extr
    START = -3
    SRC_STRING = @Value(CASEID)
    END = -1
    -> AttributeCreator
AttributeCreator
    ATTR_LIST = MothersID,@Value(_HHID_Extr).@Trim(@Value(_CaseID_Idx_Extr)),ChildID,@Value(_HHID_Extr).@Trim(@Value(_CaseID_Idx_Extr)).@Value(BORD)
    -> AttributeRenamer_9
AttributeRenamer_9
    ATTR_LIST = BORD,ChildBirthOrder,
    -> FeatureMerger_18 [input 1]
AttributeCreator_4 [off]
    ATTR_LIST = MothersID,@Value(CASEID),ChildID,@Value(CASEID).@Value(BORD)
Note: Read the points shapefile for the required survey if one exists
BDGE61FL (reader SHAPE_2)
    attributes: DHSID char(254), DHSCC char(254), DHSYEAR number(16,6), DHSCLUST number(16,6), CCFIPS char(254), ADM1FIPS char(254), ADM1FIPSNA char(254), ADM1SALBNA char(254), ADM1SALBCO char(254), ADM1DHS number(16,6), ADM1NAME char(254), DHSREGCO number(16,6), DHSREGNA char(254), SOURCE char(254), URBAN_RURA char(254), LATNUM number(16,6), LONGNUM number(16,6), ALT_GPS number(16,6), ALT_DEM number(16,6), DATUM char(254)
    -> AttributeExposer
    -> AttributeKeeper_16
AttributeKeeper_16
    KEEP_ATTRS = DHSCLUST,LATNUM,LONGNUM
    -> FeatureMerger_18 [input 2]
Note: NB / It is the responsibility of the user or caller to ensure the correct shapefile feature type name is provided. / The match is only done on cluster id which isn't unique between different surveys! A dummy value such as N/A must be provided if / no point shapefile is available otherwise it will read all!
FeatureMerger_18
    IGNORE_NULLS = No
    MERGE_TYPE = Attributes Only
    SUPPLIERS_FIRST = No
    ATTR_CONFLICT_RES = Use Requestor
    ATTR_ACCUM_MODE = Merge Supplier
    PROCESS_DUPS = Yes
    GEOM_TYPE = Build Polygons
    JOIN_KEYS = @Value(ClusterNum) @Value(DHSCLUST) AUTO
    MERGED -> NullAttributeMapper
    NOT_MERGED -> NullAttributeMapper
NullAttributeMapper
    ATTRLIST = Amodiaquine Artemether Artemisinin Artesunate ChildFullyVaccinated Chloroquine Combination of Chloroquine and Fansidar (Homapak) FeverTookACT FeverTookACTQuickly FeverTookOtherAM Mefloquine Other anti-malarial Primaquine Quinine SP/Fansidar YoungChildHadFever
    NEW_VALUE = 0
    SOURCE_ATTR_VAL = "Missing (Selected Attributes Only)"
    ATTRCHOICE = Selected Attributes
    NULL_TREATMENT = New Value
    -> AttributeValueMapper_4
AttributeValueMapper_4
    VAL_ATTR = SexOfChild
    LUT = 1,M,2,F
    SRC = SexOfChild
    DIRECTION = Forward (Source To Destination)
    -> VariableRetriever_3
VariableRetriever_3
    SCOPE = Global
    VALUE_ATTR = filecode
    VARNAME = currentFileCode
    -> AttributeCreator_2
Note: Set output names for dynamic writers
AttributeCreator_2
    ATTR_LIST = outTableName_ByChild,@Value(filecode)_ACT_By_Child_Table
    -> Kiddywinks (writer CSV_12)
Kiddywinks (writer CSV_12)
    attributes: CASEID auto, MothersID char(22), ChildID char(21), Region char(12), CountryPhase char(12), ClusterNum char(12), LATNUM number(17,10), LONGNUM number(17,10), WmnSampleWeight number(16,10), YearOfInterview char(4), MonthOfInterview char(4), HeadOfHouseholdID char(12), HeadEducationLevelDesc char(20), Wealth factor decimal int, Wealth factor quintile int, MothersAge int, MothersEducationLevelDesc text, ChildYearOfBirth char(6), ChildMonthOfBirth char(4), ChildBirthOrder int, SexOfChild char(1), ChildFullyVaccinated logical, YoungChildHadFever logical, FeverTookOtherAM logical, FeverTookACT logical, FeverTookACTQuickly logical, SP/Fansidar logical, Chloroquine logical, Amodiaquine logical, Quinine logical,
      Artesunate logical, Artemisinin logical, Artemether logical, Combination of Chloroquine and Fansidar (Homapak) logical, Mefloquine logical, Primaquine logical, Other anti-malarial logical

Bookmark: Parse record 21 - individual children
Note: CSV: REC21 [CSV]
CSV (reader CSV_1)
    attributes: B3 number(5,0), B2 number(5,0), B1 number(3,0), B0 number(2,0), BORD number(2,0), CASEID char(9), B16 number(3,0), BIDX number(2,0), B15 number(2,0), B13 number(2,0), B12 number(4,0), B11 number(4,0), B10 number(2,0), B9 number(2,0), B8 number(3,0), B7 number(4,0), B6 number(4,0), B5 number(2,0), B4 number(2,0)
    -> AttributeKeeper_2
AttributeKeeper_2
    KEEP_ATTRS = B1,B2,B3,B5,B8,BIDX,BORD,CASEID,B4
    -> AttributeCreator_10
AttributeCreator_10
    ATTR_LIST = ChildIDX,@Value(CASEID).@Value(BIDX)
    -> AttributeRenamer_8
AttributeRenamer_8
    ATTR_LIST = B3,DoBOfChild_CMC,,B1,ChildMonthOfBirth,,B2,ChildYearOfBirth,,B4,SexOfChild,
    -> DuplicateRemover_2
DuplicateRemover_2
    KEYATTR = ChildIDX
    UNIQUE -> Tester
    DUPLICATE -> Terminator_4
Note: Child is alive?
Tester
    TEST_CLAUSE = TEST @Value(B5) = 1
    BOOL_OP = OR
    TEST_DESCRIPTION = ""
    TEST_MODE = Automatic
    PASSED -> Tester_4
Note: Child is less than or equal specified age?
Tester_4
    TEST_CLAUSE = TEST @Value(B8) <= $(MaxAge)
    BOOL_OP = OR
    TEST_DESCRIPTION = ""
    TEST_MODE = Automatic
    PASSED -> AttributeKeeper_4
AttributeKeeper_4
    KEEP_ATTRS = BORD,CASEID,ChildIDX,ChildMonthOfBirth,ChildYearOfBirth,DoBOfChild_CMC,SexOfChild
    -> AttributeKeeper_19
    -> FeatureMerger [input 1]
Terminator_4
    MESSAGE = Child ID (caseid and bidx) not unique!

Bookmark: Parse record 43 - health / illness incidents in children and RECML - malaria in children
AttributeKeeper_19
    KEEP_ATTRS = ChildIDX
    -> FeatureMerger_3 [input 2]
Note: REC43: / Individual child health record
CSV (reader CSV_2)
    attributes: H12B number(2,0), H12C number(2,0), H12D number(2,0), H12E number(2,0), H12F number(2,0), H12G number(2,0), H12H number(2,0), H12I number(2,0), H12J number(2,0), H12K number(2,0), H12L number(2,0), H12M number(2,0), H12N number(2,0), H12O number(2,0), H12P number(2,0), H12Q char(1), H12R char(1), H12S number(2,0), H12T number(2,0), H12U number(2,0), H12V number(2,0), H12W char(1), H12X number(2,0), H12Y number(2,0), H12Z number(2,0), H13 number(2,0), H13B char(1), H14 number(2,0), H15 char(1), H15A char(1),
      H15B char(1), H15C char(1), H15D char(1), H15E char(1), H15F char(1), H15G char(1), H15H char(1), H15I char(1), H15J char(1), H15K char(1), H15L char(1), H15M char(1), H20 char(1), H21A char(1), H21 char(1), H22 number(2,0), H31 number(2,0), H31B number(2,0), H31C number(2,0), H31D number(2,0), H31E number(2,0), H32A number(2,0), H32B number(2,0), H32C number(2,0), H32D number(2,0), H32E number(2,0), H32F number(2,0), H32G number(2,0), H32H number(2,0), H32I number(2,0),
      H32J number(2,0), H32K number(2,0), H32L number(2,0), H32M number(2,0), H32N number(2,0), H32O number(2,0), H32P number(2,0), H32Q char(1), H32R char(1), H32S number(2,0), H32T number(2,0), H32U number(2,0), H32V number(2,0), H32W number(2,0), H32X number(2,0), H32Y number(2,0), H32Z number(2,0), H33 number(2,0), H33D number(3,0), H33M number(3,0), H33Y number(5,0), H34 number(2,0), H35 char(1), H36A number(2,0), H36B number(2,0), H36D number(2,0), H36E char(1), H36F char(1), H37A number(2,0), H37B number(2,0),
      H37C char(1), H37D number(2,0), H37E number(2,0), H37F char(1), H37G char(1), H37H number(2,0), H37I number(2,0), H37J number(2,0), H37K number(2,0), H37L number(2,0), H37M number(2,0), H37N number(2,0), H37O number(2,0), H37P number(2,0), H37X number(2,0), H37Y number(2,0), H37Z number(2,0), H38 number(2,0), H39 number(2,0), H40 char(1), H40D char(1), H40M char(1), H40Y char(1), H41A char(1), H41B char(1), H42 number(2,0), H43 number(2,0), H44A char(1), H44B char(1), H44C char(1),
      H45 char(1), H46A number(3,0), H46B char(1), H47 char(1), H5 number(2,0), HIDX number(2,0), H1 number(2,0), H2 number(2,0), H8D number(3,0), H2D number(3,0), H2M number(3,0), H2Y number(5,0), H3 number(2,0), H3D number(3,0), H3M number(3,0), H3Y number(5,0), H4 number(2,0), H4D number(3,0), H4M number(3,0), H4Y number(5,0), H12A number(2,0), H5D number(3,0), H5M number(3,0), H5Y number(5,0), H6 number(2,0), H6D number(3,0), H6M number(3,0), H6Y number(5,0), H7 number(2,0), H7D number(3,0),
      H7M number(3,0), H7Y number(5,0), H8 number(2,0), H0 number(2,0), H9Y number(5,0), H9M number(3,0), H9D number(3,0), H9 number(2,0), H8Y number(5,0), H8M number(3,0), H36C number(2,0), CASEID char(9), H0D number(2,0), H0M number(3,0), H0Y number(5,0), H10 number(2,0), H11 number(2,0), H11B number(2,0)
    -> AttributeCreator_14
AttributeCreator_14
    ATTR_LIST = ChildIDX,@Value(CASEID).@Value(HIDX)
    -> FeatureMerger_3 [input 1]
Note: ensure that illness record pertains / to a child below specified age (which it will / if age=5 but may not if age < 5)
FeatureMerger_3
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(ChildIDX) @Value(ChildIDX) AUTO
    NOT_MERGED -> HealthRecords_ChildDeadOrTooOld
    MERGED -> AttributeKeeper_3
    MERGED -> AttributeKeeper_17
AttributeKeeper_17
    KEEP_ATTRS = CASEID,ChildIDX,H2,H3,H4,H5,H6,H7,H8,H9,HIDX
    -> Tester_11
Tester_11
    TEST_CLAUSE:
      TEST @Evaluate((@min(@Value(H2),@Value(H3),@Value(H4),@Value(H5),@Value(H6),@Value(H7),@Value(H8),@Value(H9))>=1)
      &&
      (@max(@Value(H2),@Value(H3),@Value(H4),@Value(H5),@Value(H6),@Value(H7),@Value(H8),@Value(H9))<=3)) = 1
    BOOL_OP = OR
    TEST_DESCRIPTION = ""
    TEST_MODE = Automatic
    FAILED -> AttributeCreator_12
    PASSED -> AttributeCreator_13
AttributeCreator_13
    ATTR_LIST = ChildFullyVaccinated,1
    -> AttributeKeeper_18
AttributeCreator_12
    ATTR_LIST = ChildFullyVaccinated,0
    -> AttributeKeeper_18
AttributeKeeper_3
    KEEP_ATTRS = ChildIDX,H22,H31,H31B,H31C,H32A,H32B,H32C,H32D,H32E,H32F,H32G,H32H,H32I,H32J,H32K,H32L,H32M,H32N,H32O,H32P,H32Q,H32R,H32S,H32T,H32U,H32V,H32W,H32X,H32Y,H32Z
    -> Tester_2
Note: Had fever in last 2 weeks / OR, (Optionally IIF parameter set) / Had cough AND (short breath OR probs in chest)
Note: Currently only checking H22 as all surveys were found to cover it
Tester_2
    TEST_CLAUSE:
      TEST @Value(H22) = 1
      TEST @Value(H31) BETWEEN 1,7
      TEST @Value(H31B) BETWEEN 1,7
      TEST @Value(H31C) BETWEEN 1,7
      TEST $(Use_ARI) = 1
    COMPOSITE_TEST = "1 OR (5 AND 2 AND (3 OR 4))"
    BOOL_OP = COMPOSITE
    TEST_DESCRIPTION = ""
    TEST_MODE = Automatic
    FAILED -> AttributeCreator_15
    PASSED -> AttributeKeeper_6
    PASSED -> AttributeCreator_16
AttributeCreator_16
    ATTR_LIST = YoungChildHadFever,1
    -> AttributeKeeper_18
AttributeCreator_15
    ATTR_LIST = YoungChildHadFever,0
    -> AttributeKeeper_18
AttributeKeeper_18
    KEEP_ATTRS = CASEID,ChildFullyVaccinated,ChildIDX,HIDX,YoungChildHadFever
    -> CollateChildLines
Note: Collate child sickness / vaccination record - cosmetic only
CollateChildLines: AttributeRemover
    -> FeatureMerger [input 2]
AttributeKeeper_6
    KEEP_ATTRS = CASEID,H22,HIDX,ChildIDX
    -> FeatureMerger_8 [input 1]
HealthRecords_ChildDeadOrTooOld: Inspector [off]
Note: RECML: / Individual child malaria record
CSV (reader CSV_4)
    attributes: CASEID char(9), IDXML number(2,0), ML0 number(2,0), ML1 number(3,0), ML2 number(2,0), ML11 char(1), ML12 char(1), ML13A number(2,0), ML13B number(2,0), ML13C number(2,0), ML13D number(2,0), ML13E number(2,0), ML13F char(1), ML13G char(1), ML13H number(2,0), ML13I number(2,0), ML13J number(2,0), ML13K number(2,0), ML13L number(2,0), ML13M number(2,0), ML13N char(1), ML13O char(1), ML13P char(1), ML13X number(2,0), ML13Y number(2,0), ML13Z number(2,0), ML14A char(1), ML14B char(1), ML14Y char(1), ML14Z char(1),
      ML15A char(1), ML15B char(1), ML15C char(1), ML16A number(2,0), ML16B char(1), ML16C char(1), ML17A number(2,0), ML17B char(1), ML17C char(1), ML18A char(1), ML18B char(1), ML18C char(1), ML19A char(1), ML19B char(1), ML19C char(1), ML19D char(1), ML19E char(1), ML19F char(1), ML19X char(1), ML19Y char(1), ML19Z char(1), ML20A number(2,0), ML20B char(1), ML20C char(1), ML21A char(1), ML21B char(1), ML21C char(1), ML22A char(1), ML22B char(1), ML22C char(1),
      ML23A number(2,0), ML23B char(1), ML23C char(1), ML24C char(1)
    -> AttributeCreator_17
AttributeCreator_17
    ATTR_LIST = ChildIDX,@Value(CASEID).@Value(IDXML)
    -> FeatureMerger_8 [input 2]
Note: Attach the malaria specific items to the child health record item
FeatureMerger_8
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(ChildIDX) @Value(ChildIDX) AUTO
    MERGED -> AttributeExploder

Bookmark: Interpret antimalarial questions manually via external spreadsheet
Note: Spreadsheet specifying question interpretations
Sheet1 (reader XLSXR_1)
    attributes: survey char(7), record char(6), record name char(8), recode char(6), recode desc char(74), took ACT in first 24hrs of onset of fever char(2), ACT taken for fever char(2), took a non-ACT antimalarial for fever char(2), SP/Fansidar char(2), Chloroquine char(2), Amodiaquine char(2), Quinine char(2), Artesunate char(2), Artemisinin char(2), Artemether string, Combination of Chloroquine and Fansidar (Homapak) string, Mefloquine char(2), Primaquine char(2), Other anti-malarial char(2)
    -> FeatureMerger_5 [input 1]
Note: External spreadsheet has been generated containing all variable names / labels from the malaria table RECML. This has been manually flagged to indicate for each variable whether it should be interpreted as "ACT taken", "Other antimalarial taken", "ACT taken within 24 hours", if the data file contains a response to that question. It also contains further columns to identify questions relating to specific other antimalarials i.e. to pick out all questions relating to Quinine, etc.
Sampler_2
    RATE = 1
    SAMPLE_TYPE_LONG = First N Features
    GROUP_BY = FileCode
    SAMPLED -> FeatureMerger_5 [input 2]
Note: Get the ones relating to this survey
FeatureMerger_5
    IGNORE_NULLS = No
    MERGE_TYPE = Attributes Only
    SUPPLIERS_FIRST = Yes
    ATTR_CONFLICT_RES = Use Requestor
    ATTR_ACCUM_MODE = Merge Supplier
    PROCESS_DUPS = No
    JOIN_KEYS = @Value(survey) @Value(FileCode) AUTO
    MERGED -> Tester_7
Note: In this bookmark we test for each of three output questions explicitly and independently
Note: Does this variable represent an "ACT taken" question? (according to appropriate flag column)
Note: We should only have Y in 1 of these columns!
Tester_7
    TEST_CLAUSE = TEST @LowerCase(@Value(ACT taken for fever)) = y
    BOOL_OP = OR
    TEST_DESCRIPTION = ""
    TEST_MODE = Automatic
    PASSED -> AttributeKeeper_5
    FAILED -> Tester_8
Note: Simplify, remove all but RECODE id as we only want these to filter what comes through
AttributeKeeper_5
    KEEP_ATTRS = recode
    -> FeatureMerger_4 [input 2]
    -> AttributeKeeper_5_Output
AttributeKeeper_5_Output: Inspector [off]
Note: Does this variable represent an "ACT within 24 hrs of onset" question?
Tester_8
    TEST_CLAUSE = TEST @LowerCase(@Value(took ACT in first 24hrs of onset of fever)) = y
    BOOL_OP = OR
    TEST_DESCRIPTION = ""
    TEST_MODE = Automatic
    FAILED -> Tester_9
    PASSED -> AttributeKeeper_7
AttributeKeeper_7
    KEEP_ATTRS = recode
    -> FeatureMerger_9 [input 2]
Note: Does this variable represent an "other antimalarial taken" question?
Tester_9
    TEST_CLAUSE = TEST @LowerCase(@Value(took a non-ACT antimalarial for fever)) = y
    BOOL_OP = OR
    TEST_DESCRIPTION = ""
    TEST_MODE = Automatic
    PASSED -> AttributeKeeper_8
    PASSED -> AttributeKeeper_10
AttributeKeeper_8
    KEEP_ATTRS = recode
    -> FeatureMerger_10 [input 2]

Bookmark: Work out which of the antimalarial variables we want to look at to define treatment
Note: We have a specific set of things we want to know: "was ACT therapy taken", etc. / However these are not represented by the same question (variable) in every survey, for example the ACT queastyion might be in H32E, H32F, or H32G. We don't want to use all of those becasue sometimes they mean something different! / So we create an external file which gives the description of every possible question in each survey and this is used to manually flag which variables correspond to which "thing". / This workflow then needs to read this flagging file and use it to work out which question responses should map to which output summary.
Note: RecordSpec for the overall survey, / gives the survey-specific labels allocated to each H32* variable. Generated by the DCF parser. This info is now in the database so could be read from there. The only reason for reading it here now is to get the file (survey) code to filter the interpretation spreadsheet.
CSV (reader CSV_8)
    attributes: FileCode char(7), RecordName char(6), RecordTypeValue char(4), Name char(6), Label char(65), Start number(4,0), Len number(3,0), Occurrences char(1), FMETYPE char(13)
    -> VariableSetter
VariableSetter
    VALUE = @Value(FileCode)
    SCOPE = Global
    VARNAME = currentFileCode
    -> Sampler_2

Bookmark: Interpret further antimalarial questions via pivoting
Note: We were asked after initial development to pick out several more antimalarial specific variables for summary. / We could repeat the above approach for each but as there are 15+ the workbench would become quite large with 15 more tester-merger-sampler-summariser groups. / Instead for the remainder here we use a different approach, using an AttributePivoter to generate all the output columns "on the fly". / (This could replace the stuff in the bookmark above too, but as it is less clear in the WB what is happening I have not done that)
Note: Normalise / Format the multi-columns of the treament into a layout like / recode / _treatment_name / _treatment_value / ML13A / SP/Fansidar / 1 / In other words get the standardised name (as used in spreadsheet header) for each relevant recode in this particular survey- we will later be able to group by this column to summarise the amount of each type of treatment
AttributeKeeper_10
    KEEP_ATTRS = Amodiaquine,Artemether,Artemisinin,Artesunate,Chloroquine,Combination of Chloroquine and Fansidar (Homapak),Mefloquine,Other anti-malarial,Primaquine,Quinine,SP/Fansidar,recode
    -> AttributeExploder_2
AttributeExploder_2
    ATTR_NAME_LABEL = _treatment_name
    KEEP_GEOMETRY = No
    ATTR_VALUE_LABEL = _treatment_value
    KEEP_ATTRIBUTES = Yes
    EXPLODING_TYPE = Features
    -> AttributeKeeper_9
AttributeKeeper_9
    KEEP_ATTRS = recode,_treatment_name,_treatment_value
    -> AttributeValueMapper_2
AttributeValueMapper_2
    DEFAULT_VALUE = 0
    VAL_ATTR = _treatment_value
    LUT = Y,1,y,1
    SRC = _treatment_value
    DIRECTION = Forward (Source To Destination)
    -> Tester_5
Tester_5
    TEST_CLAUSE = TEST @Value(_treatment_value) = 1
    BOOL_OP = OR
    TEST_DESCRIPTION = ""
    TEST_MODE = Automatic
    PASSED -> FeatureMerger_11 [input 2]
Note: For each yes answer, about other antimalarials, get the name of the antimalarial (as specified in the columns of the spreadsheet)
FeatureMerger_11
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(_attr_name) @Value(recode) AUTO
    DUPLICATE_SUPPLIER -> Terminator
    MERGED -> AttributeRemover_4
AttributeRemover_4
    REMOVE_ATTRS = _attr_name,_attr_value
    -> AttributeKeeper_11
AttributeKeeper_11
    KEEP_ATTRS = _treatment_name,_treatment_value,CASEID,recode,ChildIDX
    -> AttributePivoter
Note: Summarise by child AND treatment name: this automatically generates one row for each child (like statistics calculator) and one column for each treatment i.e. it summarises all at once into one column for each input value. / This was to summarise by WOMAN but they changed their mind and only want it by child now. So now we summarise by CHILD and so this really only removes attributes.
AttributePivoter
    GROUP_TOTALS_TAG = Total
    PIVOT_ATTR = _treatment_value
    COLUMN_GROUP_ATTR = _treatment_name
    PIVOT_SUMMARY_TYPES = Count
    ROW_GROUP_ATTRS = ChildIDX
    DATA -> AttributePivoter_Data
    DATA -> AttributeExposer_2
Note: To work with the column attribs (i.e. treatment names) in the workbench we need to expose them otherwise they aren't known till runtime so we wouldn't be able to sum by cluster/region / This needs to be kept in sync with the names given in the spreadsheet column headers!
AttributeExposer_2
    ATTR_LIST = Amodiaquine,Artemether,Artemisinin,Artesunate,Chloroquine,"Combination of Chloroquine and Fansidar (Homapak)",Mefloquine,"Other anti-malarial",Primaquine,Quinine,SP/Fansidar
    -> CollateChildLines_2
AttributePivoter_Data: Inspector [off]
Note: The recode-name mapping should be unique
Terminator
    MESSAGE = Spreadsheet specifies that the recode is two different types of treatment! Cannot interpret.

Bookmark: Accumulate results onto child records
Note: Attach each of the different health summaries to each child / Each has a different variable name so we allow multiple suppliers to attach them all
FeatureMerger
    IGNORE_NULLS = No
    MERGE_TYPE = Attributes Only
    SUPPLIERS_FIRST = No
    ATTR_CONFLICT_RES = Use Requestor
    ATTR_ACCUM_MODE = Merge Supplier
    PROCESS_DUPS = Yes
    GEOM_TYPE = Build Polygons
    JOIN_KEYS = @Value(ChildIDX) @Value(ChildIDX) AUTO
    MERGED -> FeatureMerger_17 [input 1]
    NOT_MERGED -> FeatureMerger_17 [input 1]
Note: Attach the woman (mother) info to the child / Each has a different variable name so we allow multiple suppliers to attach them all
FeatureMerger_17
    IGNORE_NULLS = No
    MERGE_TYPE = Attributes Only
    SUPPLIERS_FIRST = No
    ATTR_CONFLICT_RES = Use Requestor
    ATTR_ACCUM_MODE = Merge Supplier
    PROCESS_DUPS = Yes
    GEOM_TYPE = Build Polygons
    JOIN_KEYS = @Value(CASEID) @Value(CASEID) AUTO
    MERGED -> StatisticsCalculator_4
    MERGED -> StatisticsCalculator_2
    MERGED -> SubstringExtractor
Note: The CaseID is always the HHID plus three characters (padded inbetween with spaces where necessary)
SubstringExtractor
    RESULT_ATTR = _HHID_Extr
    START = 0
    SRC_STRING = @Value(CASEID)
    END = -4
    -> FeatureMerger_16 [input 1]
FeatureMerger_16
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(_HHID_Extr) @Value(HHID) AUTO
    NOT_MERGED -> Terminator_5
    DUPLICATE_SUPPLIER -> Terminator_5
    MERGED -> SubstringExtractor_2
Terminator_5
    MESSAGE = Translation Terminated

Bookmark: Parse record 01 - individual (woman) respondent
Note: CSV: REC01 [CSV]
CSV (reader CSV_3)
    attributes: V026 number(2,0), V029 number(2,0), V030 number(3,0), V031 number(3,0), V000 char(4), V034 number(2,0), V040 number(3,0), V042 number(2,0), V044 char(1), V032 number(2,0), V028 number(4,0), V027 number(2,0), V025 number(2,0), V024 number(2,0), V023 number(3,0), V022 number(3,0), V021 number(3,0), V020 number(2,0), V019A number(2,0), V019 number(3,0), V018 number(3,0), V017 number(5,0), V016 number(3,0), V015 number(2,0), V014 number(2,0), V012 number(3,0), V013 number(2,0), CASEID char(9), V001 number(3,0), V002 number(4,0),
      V003 number(3,0), V004 number(3,0), V005 number(7,0), V006 number(3,0), V007 number(5,0), V008 number(5,0), V009 number(3,0), V010 number(5,0), V011 number(5,0)
    -> AttributeKeeper
Note: keep on ly the variables we're interested in
AttributeKeeper
    KEEP_ATTRS = CASEID,V000,V001,V002,V007,V012,V024,V005
    -> REC01
    -> AttributeRenamer_6
AttributeRenamer_6
    ATTR_LIST = V000,CtryCodePhase,,V001,ClusterNum,,V002,HouseholdNum,,V007,InterviewYr,,V012,MothersAge,,V024,Region,,V005,WmnSampleWeight,
    -> FeatureMerger_12 [input 2]
REC01: Inspector [off]

Bookmark: Parse record 11 - individual (woman) responsent further info (Education)
Note: CSV: REC11 (Respondent's Basic Data Continued - for woman's education)
CSV (reader CSV_7)
    attributes: CASEID char(8), V101 number(3,0), V102 number(2,0), V103 char(1), V104 char(1), V105 char(1), V106 number(2,0), V107 number(2,0), V113 number(3,0), V115 number(4,0), V116 number(3,0), V119 number(2,0), V120 number(2,0), V121 number(2,0), V122 number(2,0), V123 number(2,0), V124 number(2,0), V125 number(2,0), V127 number(3,0), V128 number(3,0), V129 number(3,0), V130 number(3,0), V131 char(1), V133 number(3,0), V134 char(1), V135 number(2,0), V136 number(3,0), V137 number(2,0), V138 number(2,0), V139 number(3,0),
      V140 number(2,0), V141 char(1), V149 number(2,0), V150 number(3,0), V151 number(2,0), V152 number(3,0), V153 number(2,0), AWFACTT number(4,0), AWFACTU number(4,0), AWFACTR number(4,0), AWFACTE number(4,0), AWFACTW number(4,0), V155 number(2,0), V156 number(2,0), V157 number(2,0), V158 number(2,0), V159 number(2,0), V160 number(2,0), V161 number(3,0), V166 char(1), V167 number(3,0), V168 number(2,0), V190 number(2,0), V191 number(8,0), ML101 number(2,0)
    -> AttributeKeeper_14
AttributeKeeper_14
    KEEP_ATTRS = CASEID,V106
    -> AttributeRenamer_5
AttributeRenamer_5
    ATTR_LIST = V106,MothersEducationLevel,
    -> AttributeValueMapper_3
AttributeValueMapper_3
    DEFAULT_VALUE = Woman_Educ_Missing
    VAL_ATTR = MothersEducationLevelDesc
    LUT = 0,Woman_Educ_None,1,Woman_Educ_Primary,2,Woman_Educ_Secondary,3,Woman_Educ_Higher
    SRC = MothersEducationLevel
    DIRECTION = Forward (Source To Destination)
    -> FeatureMerger_12 [input 1]
FeatureMerger_12
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(CASEID) @Value(CASEID) AUTO
    MERGED -> FeatureMerger_17 [input 2]

Bookmark: Accumulate and summarise child results by cluster (point location)
Note: summarise by cluster (V001), also grouping by country (V000) and region (V024) so that these carry thru
StatisticsCalculator_4
    COUNT_ATTR = ClusterCount
    GROUP_BY = ClusterNum CtryCodePhase Region
    STATS_ATTRS = Amodiaquine Artemether Artemisinin Artesunate ChildFullyVaccinated Chloroquine Combination of Chloroquine and Fansidar (Homapak) FeverTookACT FeverTookACTQuickly FeverTookOtherAM Mefloquine Other anti-malarial Primaquine Quinine SP/Fansidar YoungChildHadFever ChildIDX
    SUM_ATTR = ClusterSum
    PREPEND_ATTR_NAME_CHOICE = For multiple results only
    COMPUTE_HISTOGRAM = NO
    SUMMARY -> BulkAttributeRenamer
Note: remove illegal chars (for feature classes) from attribute names and replace with underscore
BulkAttributeRenamer
    REPLACE_STR = _
    ATTRCHOICE = All Attributes
    REPLACE_PATTERN = " |\\(|\\)|-|/|\\."
    PATTERN_ACTION_DISP = Regular Expression Replace
    -> AttributeRenamer
AttributeRenamer
    ATTR_LIST = Region,region_v024,,CtryCodePhase,ctry_phase,,ChildIDX_ClusterCount,LiveYoungChildren_ClusterSum,
    -> Results_by_cluster
    -> VariableRetriever
Results_by_cluster: Inspector [off]
VariableRetriever
    SCOPE = Global
    VALUE_ATTR = filecode
    VARNAME = currentFileCode
    -> AttributeCreator_3
Note: Set output names for dynamic writers
AttributeCreator_3
    ATTR_LIST = outTableName,@Value(filecode)_ACT_By_Cluster_Table,outFCClusterName,@Value(filecode)_ACT_By_Cluster
    -> File1 (writer CSV_11)
    -> FeatureMerger_2 [input 2]
Note: Write CSV output results (always)
File1 (writer CSV_11)
    attributes: filecode text, region_v024 text, ClusterNum int, LiveYoungChildren_ClusterSum int, YoungChildHadFever_ClusterSum int, FeverTookACT_ClusterSum int, FeverTookACTQuickly_ClusterSum int, FeverTookOtherAM_ClusterSum int, ChildFullyVaccinated_ClusterSum int, Amodiaquine_ClusterSum int, Artemether_ClusterSum int, Artemisinin_ClusterSum int, Artesunate_ClusterSum int, Chloroquine_ClusterSum int, Combination_of_Chloroquine_and_Fansidar__Homapak__ClusterSum int, Mefloquine_ClusterSum int, Other_anti_malarial_ClusterSum int, Primaquine_ClusterSum int, Quinine_ClusterSum int, SP_Fansidar_ClusterSum int
AttributeExposer
    ATTR_LIST = fme_basename
    -> FeatureMerger_2 [input 1]
Note: NB / It is the responsibility of the user or caller to ensure the correct shapefile feature type name is provided. / The match is only done on cluster id which isn't unique between different surveys! A dummy value such as N/A must be provided if / no point shapefile is available otherwise it will read all!
FeatureMerger_2
    IGNORE_NULLS = No
    MERGE_TYPE = Attributes Only
    SUPPLIERS_FIRST = No
    ATTR_CONFLICT_RES = Use Requestor
    ATTR_ACCUM_MODE = Merge Supplier
    PROCESS_DUPS = Yes
    GEOM_TYPE = Build Polygons
    JOIN_KEYS = @Value(DHSCLUST) @Value(ClusterNum) AUTO
    MERGED -> Results_Points
    MERGED -> FeatureClass1 (writer FILEGDB_2)
    MERGED -> FeatureClass1 (writer GEODATABASE_FILE_1)
Note: Write point featureclass results if any
FeatureClass1 (writer FILEGDB_2)
    attributes: filecode text(12), region_v024 text(4), ClusterNum int, LiveYoungChildren_ClusterSum int, YoungChildHadFever_ClusterSum int, FeverTookACT_ClusterSum int, FeverTookACTQuickly_ClusterSum int, FeverTookOtherAM_ClusterSum int, ChildFullyVaccinated_ClusterSum int, Amodiaquine_ClusterSum int, Artemether_ClusterSum int, Artemisinin_ClusterSum int, Artesunate_ClusterSum int, Chloroquine_ClusterSum int, Combination_of_Chloroquine_and_Fansidar__Homapak__ClusterSum int, Mefloquine_ClusterSum int, Other_anti_malarial_ClusterSum int, Primaquine_ClusterSum int, Quinine_ClusterSum int, SP_Fansidar_ClusterSum int
Results_Points: Inspector [off]
FeatureClass1 (writer GEODATABASE_FILE_1)
    attributes: filecode char(12), LiveYoungChildren_ClusterSum integer, YoungChildHadFever_ClusterSum integer, FeverTookACT_ClusterSum integer, FeverTookACTQuickly_ClusterSum integer, FeverTookOtherAM_ClusterSum integer, ChildFullyVaccinated_ClusterSum integer, region_v024 char(4), ClusterNum integer, Amodiaquine_ClusterSum integer, Artemether_ClusterSum integer, Artemisinin_ClusterSum integer, Artesunate_ClusterSum integer, Chloroquine_ClusterSum integer, Combination_of_Chloroquine_and_Fansidar__Homapak__ClusterSum integer, Mefloquine_ClusterSum integer, Other_anti_malarial_ClusterSum integer, Primaquine_ClusterSum integer, Quinine_ClusterSum integer, SP_Fansidar_ClusterSum integer

Bookmark: Accumulate and summarise by region (polygon)
Note: summarise by region V024, also grouping by country V000 so that these carry thru
StatisticsCalculator_2
    COUNT_ATTR = RegionCount
    GROUP_BY = CtryCodePhase Region
    STATS_ATTRS = Amodiaquine Artemether Artemisinin Artesunate ChildFullyVaccinated Chloroquine Combination of Chloroquine and Fansidar (Homapak) FeverTookACT FeverTookACTQuickly FeverTookOtherAM Mefloquine Other anti-malarial Primaquine Quinine SP/Fansidar YoungChildHadFever ChildIDX
    SUM_ATTR = RegionSum
    PREPEND_ATTR_NAME_CHOICE = For multiple results only
    COMPUTE_HISTOGRAM = NO
    SUMMARY -> BulkAttributeRenamer_2
Note: remove illegal chars from attribute names
BulkAttributeRenamer_2
    REPLACE_STR = _
    ATTRCHOICE = All Attributes
    REPLACE_PATTERN = " |\\(|\\)|-|/|\\."
    PATTERN_ACTION_DISP = Regular Expression Replace
    -> AttributeRenamer_2
AttributeRenamer_2
    ATTR_LIST = Region,region_v024,,CtryCodePhase,ctry_phase,,ChildIDX_RegionCount,LiveYoungChildren_RegionSum,
    -> VariableRetriever_2
VariableRetriever_2
    SCOPE = Global
    VALUE_ATTR = filecode
    VARNAME = currentFileCode
    -> AttributeCreator_7
Note: Set output name for dynamic writer
AttributeCreator_7
    ATTR_LIST = outFCRegionName,@Value(filecode)_ACT_By_Region
    -> FeatureMerger_6 [input 1]
Note: Read DHS survey identifier mapping file (provided by DHS and modified) to / work out which polygons are associated with this survey file
CSV (reader CSV_9)
    attributes: SurveyFilename char(7), Country char(22), Year char(8), Survey_ID_num number(4,0), SurveyAPI_ID char(10), Type char(4)
    -> FeatureMerger_6 [input 2]
Note: From the survey filename e.g. BDIR61 get the numeric DHS survey identifier as used in the regional boundaries
FeatureMerger_6
    IGNORE_NULLS = No
    MERGE_TYPE = Attributes Only
    SUPPLIERS_FIRST = No
    ATTR_CONFLICT_RES = Use Requestor
    ATTR_ACCUM_MODE = Merge Supplier
    PROCESS_DUPS = No
    JOIN_KEYS = @LowerCase(@Value(filecode)) @LowerCase(@Value(SurveyFilename)) AUTO
    MERGED -> FeatureMerger_7 [input 2]
    NOT_MERGED -> FeatureMerger_6_NotMerged
FeatureMerger_6_NotMerged: Inspector
Note: Read all DHS boundaries (downloaded and combined previously)
dhs_subnational_boundaries_all_surveys (reader FILEGDB_1)
    attributes: OBJECTID objectid, ISO text(2), FIPS text(2), DHSCC text(2), SVYTYPE text(3), SVYYEAR double, CNTRYNAMEE text(254), CNTRYNAMEF text(254), CNTRYNAMES text(254), DHSREGEN text(254), DHSREGFR text(254), DHSREGSP text(254), SVYID double, REG_ID text(15), Svy_Map text(3), MULTLEVEL text(3), LEVELRNK double, REGVAR text(254), REGCODE double, REGNAME text(254), OTHREGVAR text(254), OTHREGCO double, OTHREGNA text(254), LEVELCO text(254), LEVELNA text(254), REPALLIND text(254), REGNOTES text(254), SVYNOTES text(254), Shape_Length double, Shape_Area double
    -> FeatureMerger_7 [input 1]
Note: Attach results to boundaries by matching survey id
FeatureMerger_7
    IGNORE_NULLS = No
    MERGE_TYPE = Attributes Only
    SUPPLIERS_FIRST = No
    ATTR_CONFLICT_RES = Use Requestor
    ATTR_ACCUM_MODE = Merge Supplier
    PROCESS_DUPS = No
    JOIN_KEYS = @Value(SVYID) @Value(Survey_ID_num) AUTO @Value(REGCODE) @Value(region_v024) AUTO
    MERGED -> FeatureMerger_7_Merged
    MERGED -> FeatureClass100 (writer FILEGDB_2)
Note: Write polygon featureclass results if any
FeatureClass100 (writer FILEGDB_2)
    attributes: filecode text(12), region_v024 text(4), LiveYoungChildren_RegionSum int, YoungChildHadFever_RegionSum int, FeverTookACT_RegionSum int, FeverTookACTQuickly_RegionSum int, FeverTookOtherAM_RegionSum int, ChildFullyVaccinated_RegionSum int, Amodiaquine_RegionSum int, Artemether_RegionSum int, Artemisinin_RegionSum int, Artesunate_RegionSum int, Chloroquine_RegionSum int, Combination_of_Chloroquine_and_Fansidar__Homapak__RegionSum int, Mefloquine_RegionSum int, Other_anti_malarial_RegionSum int, Primaquine_RegionSum int, Quinine_RegionSum int, SP_Fansidar_RegionSum int
FeatureMerger_7_Merged: Inspector [off]

Bookmark: Parse household records for wealth and head's education
Note: RECH0: / Household basic data: read this to get the cluster ID, via the line number, for the data in RECH1
CSV (reader CSV_6)
    attributes: HHID char(6), HV000 char(4), HV001 number(3,0), HV002 number(3,0), HV003 number(2,0), HV004 number(3,0), HV005 number(8,0), HV006 number(2,0), HV007 number(5,0), HV008 number(5,0), HV009 number(3,0), HV010 number(2,0), HV011 char(1), HV012 number(3,0), HV013 number(3,0), HV014 number(2,0), HV015 number(2,0), HV016 number(3,0), HV017 number(2,0), HV018 number(4,0), HV019 number(3,0), HV020 number(2,0), HV021 number(3,0), HV022 number(2,0), HV023 number(2,0), HV024 number(2,0), HV025 number(2,0), HV026 char(1), HV027 char(1), HV028 char(1),
      HV030 number(4,0), HV031 number(3,0), HV032 number(2,0), HV033 char(1), HV035 number(2,0), HV040 number(5,0), HV041 char(1), HV042 number(2,0), HV043 char(1), HV044 char(1)
    -> AttributeKeeper_13
AttributeKeeper_13
    KEEP_ATTRS = HHID,HV001,HV003,HV006,HV007,HV024,HV000
    -> AttributeRenamer_3
AttributeRenamer_3
    ATTR_LIST = HV001,ClusterNum,,HV003,RespondentLineNum,,HV024,Region,,HV006,MonthOfInterview,,HV007,YearOfInterview,,HV000,CountryPhase,
    -> FeatureMerger_13 [input 1]
Note: RECH1: / Household schedule: read this to find the education of the head of household (can't just use REC01 women's as they may not be head of household)
CSV (reader CSV_5)
    attributes: HHID char(5), HVIDX number(3,0), HV101 number(3,0), HV102 number(2,0), HV103 number(2,0), HV104 number(2,0), HV105 number(3,0), HV106 char(1), HV107 char(1), HV108 char(1), HV109 char(1), HV110 char(1), HV111 char(1), HV112 char(1), HV113 char(1), HV114 char(1), HV115 char(1), HV116 char(1), HV117 number(2,0), HV118 char(1), HV120 number(2,0), HV121 char(1), HV122 char(1), HV123 char(1), HV124 char(1), HV125 char(1), HV126 char(1), HV127 char(1), HV128 char(1), HV129 char(1),
      HV130 char(1), HV131 char(1), HV132 char(1), HV133 char(1), HV134 char(1), HV135 char(1), HV136 char(1), HV137 char(1), HV138 char(1), HV139 char(1), HV140 char(1)
    -> AttributeKeeper_12
AttributeKeeper_12
    KEEP_ATTRS = HHID,HV106,HV108,HVIDX,HV101
    -> AttributeRenamer_4
AttributeRenamer_4
    ATTR_LIST = HVIDX,LineNum,,HV101,RelToHead,,HV106,HeadEducationLevel,,HV108,HeadEducationInYrs,
    -> Tester_10
Note: Find heads of households
Tester_10
    TEST_CLAUSE = TEST @Value(RelToHead) = 1
    BOOL_OP = OR
    TEST_DESCRIPTION = ""
    TEST_MODE = Automatic
    PASSED -> DuplicateRemover
DuplicateRemover
    KEYATTR = HHID
    UNIQUE -> AttributeValueMapper
    DUPLICATE -> MessageLogger
AttributeValueMapper
    DEFAULT_VALUE = Head_Educ_Missing
    VAL_ATTR = HeadEducationLevelDesc
    LUT = 0,Head_Educ_None,1,Head_Educ_Primary,2,Head_Educ_Secondary,3,Head_Educ_Higher
    SRC = HeadEducationLevel
    DIRECTION = Forward (Source To Destination)
    -> FeatureMerger_13 [input 2]
MessageLogger
    TYPE = ERROR
    MESSAGE = A household was found with two heads! Chopped one off.
Note: RECH2: / Household characteristics: read this to find the wealth index / quintile of the household
CSV (reader CSV_10)
    attributes: HHID char(5), HV201 number(3,0), HV202 char(1), HV204 number(4,0), HV205 number(3,0), HV206 number(2,0), HV207 number(2,0), HV208 number(2,0), HV209 number(2,0), HV210 number(2,0), HV211 number(2,0), HV212 number(2,0), HV213 number(3,0), HV214 number(3,0), HV215 number(3,0), HV216 number(3,0), HV217 number(2,0), HV218 number(2,0), HV219 number(2,0), HV220 number(3,0), HV221 number(2,0), HV225 number(2,0), HV226 number(3,0), HV227 number(2,0), HV228 number(2,0), HV230A number(2,0), HV230B number(2,0), HV232 number(2,0), HV232B number(2,0), HV232C char(1),
      HV232D char(1), HV232E char(1), HV232Y number(2,0), HV234 char(1), HV234A number(2,0), HV235 number(2,0), HV236 char(1), HV237 number(2,0), HV237A number(2,0), HV237B number(2,0), HV237C number(2,0), HV237D number(2,0), HV237E char(1), HV237F number(2,0), HV237G char(1), HV237H char(1), HV237I char(1), HV237J char(1), HV237K char(1), HV237X number(2,0), HV237Z number(2,0), HV238 number(3,0), HV239 char(1), HV240 char(1), HV241 number(2,0), HV242 number(2,0), HV243A number(2,0), HV243B number(2,0), HV243C number(2,0), HV243D number(2,0),
      HV244 number(2,0), HV245 number(4,0), HV246 number(2,0), HV246A number(3,0), HV246B number(3,0), HV246C number(3,0), HV246D number(3,0), HV246E number(3,0), HV246F number(3,0), HV246G char(1), HV246H char(1), HV246I char(1), HV246J char(1), HV246K char(1), HV247 number(2,0), HV252 number(2,0), HV253 number(2,0), HV253A number(2,0), HV253B number(2,0), HV253C number(2,0), HV253D char(1), HV253E char(1), HV253F char(1), HV253G char(1), HV253H char(1), HV253X number(2,0), HV253Z number(2,0), HV270 number(2,0), HV271 number(8,0), HML1 number(2,0),
      HML1A number(2,0), HML2 number(2,0)
    -> AttributeKeeper_15
AttributeKeeper_15
    KEEP_ATTRS = HHID,HV270,HV271
    -> AttributeRenamer_7
AttributeRenamer_7
    ATTR_LIST = HV270,Wealth factor quintile,,HV271,Wealth factor decimal,
    -> FeatureMerger_13 [input 2]
FeatureMerger_13
    IGNORE_NULLS = No
    MERGE_TYPE = Attributes Only
    SUPPLIERS_FIRST = No
    ATTR_CONFLICT_RES = Use Requestor
    ATTR_ACCUM_MODE = Merge Supplier
    PROCESS_DUPS = Yes
    GEOM_TYPE = Build Polygons
    JOIN_KEYS = @Value(HHID) @Value(HHID) AUTO
    MERGED -> AttributeCreator_11
AttributeCreator_11
    ATTR_LIST = HeadOfHouseholdID,@Value(HHID).@Value(LineNum)
    -> FeatureMerger_16 [input 2]

Bookmark: Summarise relevant yes-answers
Note: Process questions that were answered yes to see if they are the questions we have determined that we're interested in.

FME custom transformer DateDifferenceCalculator_2
Calculates the difference in time between two dates.
Select Start Date Attribute, End Date Attribute and input date format string. See DateFormatter documentation for more detailed explanations of date format strings.
Also select the units you wish the time difference to be expressed in. Time Difference will be stored in _TimeDifference attribute.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTR =   # " " Start Date
- SRC_ATTR_2 =   # " " End Date
- FMT = %Y%m%d   # Input Date Format
- Unit = 86400   # Output Time Units

INPUT (input)
    -> AttributeCreator
Note: Retrieve parameters
AttributeCreator
    NUM_SUBSEQUENT_FEATURES = 0
    ATTR_LIST = DDC_StartDate,@Value($(SRC_ATTR)),DDC_EndDate,@Value($(SRC_ATTR_2))
    NUM_PRIOR_FEATURES = 0
    -> DateFormatter
Note: Convert temp Date Attributes / to seconds since UNIX Epoch
DateFormatter
    SRCFMT = $(FMT)
    DATE_ATTR = DDC_StartDate,DDC_EndDate
    FMT = %s
    -> ExpressionEvaluator
Note: Subtract Dates and / convert to desired unit
ExpressionEvaluator
    VAL_ATTR = _TimeDifference
    EXPRESSION = @round(1.0*(@Value(DDC_EndDate)-@Value(DDC_StartDate))/$(Unit))
    -> AttributeRemover
Note: Remove temp attributes
AttributeRemover
    REMOVE_ATTRS = DDC_StartDate,DDC_EndDate
    -> OUTPUT (output)
OUTPUT (output)
