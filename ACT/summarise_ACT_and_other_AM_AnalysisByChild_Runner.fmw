FME workspace summarise_ACT_and_other_AM_AnalysisByChild_Runner.fmw

Parameters:
- DestDataset_FILEGDB = C:\Users\zool1301\Documents\DHS\Processing\ACT\Outputs\Phase6_ACT.gdb   # Destination Geodatabase
- InputFileDir = C:\Users\zool1301\Documents\DHS\Processing_Round1\Phase6\ExtractedSurveyRecords_Python   # directory containing input extracted records
- SurveySpecDir = C:\Users\zool1301\Documents\DHS\Processing_Round1\Phase6\SurveySpecs_Final   # Directory containing survey specification files
- ShapefileDir = C:\Users\zool1301\Documents\DHS\Processing_Round1\Phase6\ExtractedSurveysAndShapes   # Directory containing survey shapefiles where available
- OutCSVDir = C:\Users\zool1301\Documents\DHS\Processing\ACT\Outputs\CSV_ACT   # Destination CSV Folder
- AllPointShapes = C:\Users\zool1301\Documents\DHS\Processing_Round1\Phase6\ExtractedSurveysAndShapes\*.shp   # All survey point shapefiles
- SurveyIDMap_CSV = C:\Users\zool1301\Documents\DHS\DHS_Info\SurveyIdsByFile_P6_All.csv   # Survey ID mapping CSV file
- VariableFlagFile = \\129.67.26.176\map_data\DHS_Automation\Processing\AntimalarialUsage_201507\Info\variable_selection_full.xlsx   # Excel file containing flagged variables
- Source_GDB_Boundaries = \\129.67.26.176\map_data\DHS_Automation\SupportingInfo\DHS_Boundary_Data\full_download\sdr_subnational_boundaries_all_surveys.gdb   # Source Geodatabase containing survey boundaries
- DestDataset_AO_GDB = C:\Users\zool1301\Documents\DHS\Processing\ACT\Outputs\Phase6_ACT_Test_AO.gdb   # Destination Esri File Geodatabase (AO writer)

Readers:
- PATH_1: PATH from $(InputFileDir)
- PATH_2: PATH from $(ShapefileDir)

Note: Read the names of all the .DAT files
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringCaseChanger
StringCaseChanger
    ATTRLIST = path_rootname
    CHANGE_TYPE = UPPERCASE
    ATTRCHOICE = Selected Attributes
    -> SubstringExtractor
SubstringExtractor
    END = 5
    START = 0
    SRC_ATTR = path_rootname
    RESULT_ATTR = _surveycode
    -> PATH
    -> SubstringExtractor_2
PATH: Inspector
SubstringExtractor_2
    END = 1
    START = 0
    SRC_ATTR = path_rootname
    RESULT_ATTR = _surveyCtryCode
    -> SubstringExtractor_5
SubstringExtractor_5
    END = 5
    START = 4
    SRC_ATTR = path_rootname
    RESULT_ATTR = _surveySurveyCode
    -> SubstringExtractor_7
SubstringExtractor_7
    END = 4
    START = 4
    SRC_ATTR = path_rootname
    RESULT_ATTR = _surveyPhaseCode
    -> SubstringExtractor_9
SubstringExtractor_9
    END = 5
    START = 5
    SRC_ATTR = path_rootname
    RESULT_ATTR = _surveyVersionCode
    -> AttributeCreator
Note: Generate parameters specofying survey files to process
AttributeCreator
    ATTR_LIST = _rec01Path,$(InputFileDir)\@Value(_surveycode).REC01.csv,_rec11Path,$(InputFileDir)\@Value(_surveycode).REC11.csv,_rec21Path,$(InputFileDir)\@Value(_surveycode).REC21.csv,_rec43Path,$(InputFileDir)\@Value(_surveycode).REC43.csv,_recH0Path,$(InputFileDir)\@Value(_surveycode).RECH0.csv,_recH1Path,$(InputFileDir)\@Value(_surveycode).RECH1.csv,_recH2Path,$(InputFileDir)\@Value(_surveycode).RECH2.csv,_recMLPath,$(InputFileDir)\@Value(_surveycode).RECML.csv,_surveySpecPath,$(SurveySpecDir)\@Value(_surveycode).FlatRecordSpec.csv,_shapefileWildcardPath,$(ShapefileDir)\*.shp
    -> AttributeKeeper_2
AttributeKeeper_2
    KEEP_ATTRS = _rec01Path,_rec21Path,_rec43Path,_recMLPath,_shapefileWildcardPath,_surveycode,_surveyCtryCode,_surveyPhaseCode,_surveySpecPath,_surveySurveyCode,_surveyVersionCode,path_rootname,_rec11Path,_recH0Path,_recH1Path,_recH2Path
    -> FeatureMerger [input 1]
Note: Read the names of all the .SHP files
PATH (reader PATH_2)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeKeeper
AttributeKeeper
    KEEP_ATTRS = path_rootname
    -> AttributeRenamer
AttributeRenamer
    ATTR_LIST = path_rootname,shp_ftname,
    -> SubstringExtractor_3
SubstringExtractor_3
    END = 1
    START = 0
    SRC_ATTR = shp_ftname
    RESULT_ATTR = _shpCtryCode
    -> SubstringExtractor_4
SubstringExtractor_4
    END = 5
    START = 4
    SRC_ATTR = shp_ftname
    RESULT_ATTR = _shpSurveyCode
    -> SubstringExtractor_6
SubstringExtractor_6
    END = 4
    START = 4
    SRC_ATTR = shp_ftname
    RESULT_ATTR = _shpPhaseCode
    -> SubstringExtractor_8
SubstringExtractor_8
    END = 5
    START = 5
    SRC_ATTR = shp_ftname
    RESULT_ATTR = _shpVersionCode
    -> FeatureMerger_2 [input 2]
    -> FeatureMerger [input 2]
Note: See if there is a shapefile with identical name to the survey file
FeatureMerger
    ATTR_ACCUM_MODE = Merge Supplier
    ATTR_CONFLICT_RES = Use Requestor
    MERGE_TYPE = Attributes Only
    JOIN_KEYS = @Value(_surveyCtryCode) @Value(_shpCtryCode) AUTO @Value(_surveySurveyCode) @Value(_shpSurveyCode) AUTO
    PROCESS_DUPS = No
    SUPPLIERS_FIRST = No
    IGNORE_NULLS = No
    MERGED -> WorkspaceRunner
    MERGED -> Clean_Match_To_Shapefile
    NOT_MERGED -> FeatureMerger_2 [input 1]
Clean_Match_To_Shapefile: Inspector
Note: If not then see if there are one or more shapefiles with the same country code and phase as the survey file
FeatureMerger_2
    ATTR_ACCUM_MODE = Merge Supplier
    ATTR_CONFLICT_RES = Use Requestor
    MERGE_TYPE = Attributes Only
    JOIN_KEYS = @Value(_surveyCtryCode) @Value(_shpCtryCode) AUTO @Value(_surveyPhaseCode) @Value(_shpPhaseCode) AUTO
    PROCESS_DUPS = No
    SUPPLIERS_FIRST = No
    IGNORE_NULLS = No
    LIST_NAME = _list
    NOT_MERGED -> No_Shapefile
    NOT_MERGED -> AttributeCreator_2
    MERGED -> AttributeKeeper_3
AttributeKeeper_3
    KEEP_ATTRS = _rec01Path,_rec21Path,_rec43Path,_shapefileWildcardPath,_surveycode,_surveyCtryCode,_surveyPhaseCode,_surveySpecPath,_surveySurveyCode,_surveyVersionCode,path_rootname,_rec11Path,_recH0Path,_recH1Path,_recH2Path,_recMLPath
    KEEP_LIST = _list{}
    -> ListExploder
ListExploder
    ATTR_ACCUM_MODE = Merge Incoming List
    ATTR_CONFLICT_RES = Use Incoming List
    LIST_ATTR = _list{}
    LIST_FOUND -> CharacterCodeExtractor
Note: If there's more than one shapefile of same country code and phase pick the one with the closest version id, unless the version is more than 8 different in which case reject the match
CharacterCodeExtractor
    CODE_ATTR = _shpVersionCodeAscii
    SRC_ATTR = _shpVersionCode
    -> CharacterCodeExtractor_2
CharacterCodeExtractor_2
    CODE_ATTR = _surveyVersionCodeAscii
    SRC_ATTR = _surveyVersionCode
    -> AttributeCreator_3
AttributeCreator_3
    ATTR_LIST = _surveyShpVersionDiff,@Evaluate(@abs(@Value(_shpVersionCodeAscii)-@Value(_surveyVersionCodeAscii)))
    -> Sorter
Sorter
    SORT_PARM = path_rootname ALPHA ASCENDING _surveyShpVersionDiff NUMERIC ASCENDING
    SORTED -> Sampler
Sampler
    RATE = 1
    GROUP_BY = path_rootname
    SAMPLE_TYPE_LONG = First N Features
    SAMPLED -> Tester
Tester
    BOOL_OP = OR
    TEST_DESCRIPTION = ""
    TEST_MODE = Automatic
    TEST_CLAUSE = TEST @Value(_surveyShpVersionDiff) < 8
    PASSED -> InexactShape_ThisOneSelected
    PASSED -> WorkspaceRunner
    FAILED -> AttributeCreator_2
    FAILED -> InexactShp_NoneSelected
InexactShape_ThisOneSelected: Inspector
InexactShp_NoneSelected: Inspector
Note: 'If there is no matching shapefile then put a dummy value in the workspace parameter else it will read ALL shapefiles!
AttributeCreator_2
    ATTR_LIST = shp_ftname,N/A
    -> WorkspaceRunner
Note: Run the workbench!
WorkspaceRunner
    BLOCKING = Yes
    WORKSPACE_FILE = $(FME_MF_DIR)summarise_ACT_and_other_AM_AnalysisByChild.fmw
    WORKSPACE_PARAMETERS = REC01_CSV,@Value(_rec01Path),REC11_CSV,@Value(_rec11Path),REC21_CSV,@Value(_rec21Path),REC43_CSV,@Value(_rec43Path),RECML_CSV,@Value(_recMLPath),RECH0_CSV,@Value(_recH0Path),RECH1_CSV,@Value(_recH1Path),RECH2_CSV,@Value(_recH2Path),MaxAge,5,SurveyIDMap_CSV,$(SurveyIDMap_CSV),SurveyRecordSpec,@Value(_surveySpecPath),VariableSelectionXLS,$(VariableFlagFile),AllPointShapes,$(AllPointShapes),SURVEY_GPS_FEAT_TYPE,@Value(shp_ftname),Source_GDB_Boundaries,$(Source_GDB_Boundaries),OutGDB_Name,$(DestDataset_FILEGDB),OutCSVDir,$(OutCSVDir),Use_ARI,0,DestDataset_GEODATABASE_FILE,$(DestDataset_AO_GDB)
    SUCCEEDED -> WorkspaceRunner_Succeeded
    FAILED -> WorkspaceRunner_Failed
    SUMMARY -> WorkspaceRunner_Summary
WorkspaceRunner_Succeeded: Inspector
WorkspaceRunner_Failed: Inspector
WorkspaceRunner_Summary: Inspector
No_Shapefile: Inspector
